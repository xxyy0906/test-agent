-- 2.1 MIB Header

-- Filename:    1202v0218.mib
-- Description: This MIB defines defines those objects which are specifically 
--              used by actuated traffic signal controllers.  
-- Source:      NTCIP 1202 v02.18
-- MIB Revision History:
-- 09/27/04     Created file form Word .Doc file.  
--              Changed module name to NTCIP1202-200x to NTCIP1202-2004
--              Changes status of objects to mandatory to eliminate incompatible status errors
--              Restructured IMPORTS to use NTCIP8004-A-2004 instead of TMIB-II
--
--Copyright  2004 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************

NTCIP1202-2004 DEFINITIONS ::= BEGIN

-- the following OBJECT IDENTIFIERS are used in the ASC MIB:
IMPORTS
    Counter
        FROM RFC1155-SMI

    OBJECT-TYPE
        FROM RFC-1212

--    OwnerString, devices
--        FROM TMIB-II;

--asc OBJECT IDENTIFIER ::= { devices 1 }

    OwnerString, devices, asc
        FROM NTCIP8004-A-2004;

-- 2.1 PHASE PARAMETERS

phase OBJECT IDENTIFIER ::= { asc 1 }

-- This node shall contain objects that configure, monitor or 
-- control phase functions for this device.

-- 2.1.1 MAXIMUM PHASES

maxPhases   OBJECT-TYPE
   SYNTAX   INTEGER (2..255)
   ACCESS   read-only
   STATUS   mandatory
   DESCRIPTION
      "<Definition> The Maximum Number of Phases this 
       Actuated Controller Unit supports. This object 
       indicates the maximum rows which shall appear in 
       the phaseTable object.
       <DescriptiveName> NTCIP-1202::ASC.maxPhases
       <DataConceptType> Data Element
       <Unit> phase"
::= { phase 1 }

-- 2.1.2 PHASE TABLE

phaseTable   OBJECT-TYPE
   SYNTAX   SEQUENCE OF PhaseEntry
   ACCESS   not-accessible
   STATUS   mandatory
   DESCRIPTION
      "<Definition> A table containing Actuated Controller 
       Unit phase parameters. The number of rows in this 
       table is equal to the maxPhases object.
       <TableType> static
       <DescriptiveName> NTCIP-1202::ASC.phaseTable
       <DataConceptType> Entity Type"
::= { phase 2 }

phaseEntry   OBJECT-TYPE
   SYNTAX   PhaseEntry
   ACCESS   not-accessible
   STATUS   mandatory
   DESCRIPTION
      "<Definition> Parameters for a specific Actuated 
       Controller Unit phase.
       <DescriptiveName> NTCIP-1202::ASC.phaseEntry
       <DataConceptType> Entity Type
       <Unit> "
   INDEX   { phaseNumber }
::= { phaseTable 1 }


PhaseEntry ::= SEQUENCE { 
   phaseNumber                INTEGER,
   phaseWalk                  INTEGER,
   phasePedestrianClear       INTEGER,
   phaseMinimumGreen          INTEGER,
   phasePassage               INTEGER,
   phaseMaximum1              INTEGER,
   phaseMaximum2              INTEGER,
   phaseYellowChange          INTEGER,
   phaseRedClear              INTEGER,
   phaseRedRevert             INTEGER,
   phaseAddedInitial          INTEGER,
   phaseMaximumInitial        INTEGER,
   phaseTimeBeforeReduction   INTEGER,
   phaseCarsBeforeReduction   INTEGER,
   phaseTimeToReduce          INTEGER,
   phaseReduceBy              INTEGER,
   phaseMinimumGap            INTEGER,
   phaseDynamicMaxLimit       INTEGER,
   phaseDynamicMaxStep        INTEGER,
   phaseStartup               INTEGER,
   phaseOptions               INTEGER,
   phaseRing                  INTEGER,
   phaseConcurrency           OCTET STRING }

-- 2.1.2.1 PHASE NUMBER

phaseNumber   OBJECT-TYPE
   SYNTAX    INTEGER (1..255)
   ACCESS   read-only
   STATUS   mandatory
   DESCRIPTION
      "<Definition> The phase number for objects in this 
       row. This value shall not exceed the maxPhases 
       object value.
       <DescriptiveName> NTCIP-1202::ASC.phaseNumber
       <DataConceptType> Data Element
       <Unit> phase"
::= { phaseEntry 1 }

-- 2.1.2.2 PHASE WALK PARAMETER

phaseWalk   OBJECT-TYPE
   SYNTAX   INTEGER (0..255)
   ACCESS   read-write
   STATUS   mandatory
   DESCRIPTION
      "<Definition> Phase Walk Parameter in seconds. This 
       shall control the amountof time the Walk indication 
       shall be displayed.
       <DescriptiveName> NTCIP-1202::ASC.phaseWalk
       <DataConceptType> Data Element
       <Unit> second"
   REFERENCE
      "NEMA TS 2 Clause 3.5.3.1 and 3.5.3.2.2.a"
::= { phaseEntry 2 }

-- 2.1.2.3 PHASE PEDESTRIAN CLEAR PARAMETER

phasePedestrianClear   OBJECT-TYPE
   SYNTAX   INTEGER (0..255)
   ACCESS   read-write
   STATUS   mandatory
   DESCRIPTION
      "<Definition> Phase Pedestrian Clear Parameter in 
       seconds. This shall control the duration of the 
       Pedestrian Clearance output (if present) and the 
       flashing period of the Don’t Walk output.
       <DescriptiveName> NTCIP-1202::ASC.phasePedestrianClear
       <DataConceptType> Data Element
       <Unit> second"
   REFERENCE
      "NEMA TS 2 Clause 3.5.3.1 and 3.5.3.2.2.b"
::= { phaseEntry 3 }

-- 2.1.2.4 PHASE MINIMUM GREEN PARAMETER

phaseMinimumGreen   OBJECT-TYPE
   SYNTAX   INTEGER (0..255)
   ACCESS   read-write
   STATUS   mandatory
   DESCRIPTION
      "<Definition> Phase Minimum Green Parameter in 
       seconds (NEMA TS 2 range: 1-255 sec). The first 
       timed portion of the Green interval which may be 
       set in consideration of the storage of vehicles
       between the zone of detection for the approach 
       vehicle detector(s) and the stop line.
       <DescriptiveName> NTCIP-1202::ASC.phaseMinimumGreen
       <DataConceptType> Data Element
       <Unit> second"
   REFERENCE
      "NEMA TS 2 Clause 3.5.3.1 and 3.5.3.2.1.a.(1)"
::= { phaseEntry 4 }

-- 2.1.2.5 PHASE PASSAGE PARAMETER

phasePassage   OBJECT-TYPE
   SYNTAX   INTEGER (0..255)
   ACCESS   read-write
   STATUS   mandatory
   DESCRIPTION
      "<Definition> Phase Passage Parameter in tenth 
       seconds (0-25.5 sec). Passage Time, Vehicle Interval,
       Preset Gap, Vehicle Extension: the extensible portion
       of the Green shall be a function of vehicle 
       actuations that occur during the Green interval. 
       The phase shall remain in the extensible portion of 
       the Green interval as long as the passage timer is 
       not timed out.  The timing of this portion of the 
       green interval shall be reset with each subsequent 
       vehicle actuation and shall not commence to time 
       again until the vehicle actuation is removed.

       <DescriptiveName> NTCIP-1202::ASC.phasePassage
       <DataConceptType> Data Element
       <Unit> tenth second"
   REFERENCE
      "NEMA TS 2 Clause 3.5.3.1 and 3.5.3.2.1.a.(2)"
::= { phaseEntry 5 }

-- 2.1.2.6 PHASE MAXIMUM GREEN 1 PARAMETER

phaseMaximum1   OBJECT-TYPE
   SYNTAX   INTEGER (0..255)
   ACCESS   read-write
   STATUS   mandatory
   DESCRIPTION
      "<Definition> Phase Maximum 1 Parameter in seconds 
       (NEMA TS 2 range: 1-255 sec). This time setting 
       shall determine the maximum length of time this 
       phase may be held Green in the presence of a 
       serviceable conflicting call. In the absence of a 
       serviceable conflicting call the Maximum Green timer 
       shall be held reset unless Max Vehicle Recall is 
       enabled for this phase.  This is the default maximum
       value to use.  It may be overridden via an external 
       input, coordMaximumMode or other method.
       <DescriptiveName> NTCIP-1202::ASC.phaseMaximum1
       <DataConceptType> Data Element
       <Unit> second"
   REFERENCE
      "NEMA TS 2 Clause 3.5.3.1, 3.5.3.2.1.a.(3) and 3.5.3.5"
::= { phaseEntry 6 }

-- 2.1.2.7 PHASE MAXIMUM GREEN 2 PARAMETER

phaseMaximum2   OBJECT-TYPE
   SYNTAX   INTEGER (0..255)
   ACCESS   read-write
   STATUS   mandatory
   DESCRIPTION
      "<Definition> Phase Maximum 2 Parameter in seconds 
       (NEMA TS 2 range: 1-255 sec). This time setting 
       shall determine the maximum length of time this phase
       may be held Green in the presence of a serviceable 
       conflicting call. In the absence of a serviceable 
       conflicting call the Maximum Green timer shall be 
       held reset unless Max Vehicle Recall is enabled for 
       this phase.  This may be implemented as the max green
       timer via an external input, coordMaximumMode or 
       other method.
       <DescriptiveName> NTCIP-1202::ASC.phaseMaximum2
       <DataConceptType> Data Element
       <Unit> second"
   REFERENCE
      "NEMA TS 2 Clause 3.5.3.1, 3.5.3.2.1.a.(3), 3.5.3.5 
       and 3.5.4.1 (7)"
::= { phaseEntry 7 }

-- 2.1.2.8 PHASE YELLOW CHANGE PARAMETER

phaseYellowChange   OBJECT-TYPE
   SYNTAX   INTEGER (0..255)
   ACCESS   read-write
   STATUS   mandatory
   DESCRIPTION
      "<Definition> Phase Yellow Change Parameter in tenth 
       seconds (NEMA TS 2 range: 3-25.5 sec). Following the
       Green interval of each phase the CU shall provide a 
       Yellow Change interval which is timed according to 
       the Yellow Change parameter for that phase.
       <DescriptiveName> NTCIP-1202::ASC.phaseYellowChange
       <DataConceptType> Data Element
       <Unit> tenth second"
   REFERENCE
      "NEMA TS 2 Clause 3.5.3.1 and 3.5.3.2.5.a"
::= { phaseEntry 8 }

-- 2.1.2.9 PHASE RED CLEAR PARAMETER

phaseRedClear   OBJECT-TYPE
   SYNTAX   INTEGER (0..255)
   ACCESS   read-write
   STATUS   mandatory
   DESCRIPTION
      "<Definition> Phase Red Clearance Parameter in tenth 
       seconds (0-25.5 sec).Following the Yellow Change 
       interval for each phase, the CU shall provide a Red 
       Clearance interval which is timed according to the 
       Red Clearance parameter for that phase.
       <DescriptiveName> NTCIP-1202::ASC.phaseRedClear
       <DataConceptType> Data Element
       <Unit> tenth second"
   REFERENCE
      "NEMA TS 2 Clause 3.5.3.1 and 3.5.3.2.5.b"
::= { phaseEntry 9 }

-- 2.1.2.10 PHASE RED REVERT

phaseRedRevert OBJECT-TYPE
   SYNTAX   INTEGER (0..255) 
   ACCESS   read-write
   STATUS   mandatory
   DESCRIPTION
      "<Definition> Red revert time parameter in tenth 
       seconds .  A minimum Red indication to be timed 
       following the Yellow Change interval and prior to 
       the next display of Green on the same signal output 
       driver group.

       The unitRedRevert parameter shall act as a minimum 
       red revert time for all signal displays.  The 
       phaseRedRevert parameter may increase the red revert
       time for a specific phase.  If the phaseRedRevert 
       parameter is less than the unitRedRevert the 
       unitRedRevert time shall be used.
       <DescriptiveName> NTCIP-1202::ASC.phaseRedRevert
       <DataConceptType> Data Element
       <Unit> tenth second"
::= { phaseEntry 10 }

-- 2.1.2.11 PHASE ADDED INITIAL PARAMETER

phaseAddedInitial   OBJECT-TYPE
   SYNTAX   INTEGER (0..255)
   ACCESS   read-write
   STATUS   mandatory
   DESCRIPTION
      "<Definition> Phase Added Initial Parameter in tenths
       of seconds (0-25.5 sec). Added Initial parameter 
       (Seconds / Actuation) shall determine the time by 
       which the variable initial time period will be 
       increased from zero with each vehicle actuation 
       received during the associated phase Yellow and Red 
       intervals.
       <DescriptiveName> NTCIP-1202::ASC.phaseAddedInitial
       <DataConceptType> Data Element
       <Unit> tenth second"
   REFERENCE
      "NEMA TS 2 Clause 3.5.3.1 and 3.5.3.2.1.b.(1).(b)"
::= { phaseEntry 11 }

-- 2.1.2.12 PHASE MAXIMUM INITIAL PARAMETER

phaseMaximumInitial   OBJECT-TYPE
   SYNTAX   INTEGER (0..255)
   ACCESS   read-write
   STATUS   mandatory
   DESCRIPTION
      "<Definition> Phase Maximum Initial Parameter in 
       seconds (0-255 sec). The maximum value of the 
       variable initial timing period. Variable Initial 
       timing shall equal the lesser of [added initial 
       (seconds / actuation) * number of actuations] or 
       [ Max Initial ]. The variable initial time shall not
       be less than Minimum Green.
       <DescriptiveName> NTCIP-1202::ASC.phaseMaximumInitial
       <DataConceptType> Data Element
       <Unit> second"
   REFERENCE
      "NEMA TS 2 Clause 3.5.3.2.1.b.(1).(c)"
::= { phaseEntry 12 }

-- 2.1.2.13 PHASE TIME BEFORE REDUCTION PARAMETER

phaseTimeBeforeReduction   OBJECT-TYPE
   SYNTAX   INTEGER (0..255)
   ACCESS   read-write
   STATUS   mandatory
   DESCRIPTION
      "<Definition> Phase Time Before Reduction (TBR) 
       Parameter in seconds (0-255 sec). The Time Before 
       Reduction period shall begin when the phase is Green
       and there is a serviceable conflicting call. If the 
       serviceable conflicting call is removed before 
       completion of this time (or time to reduce), the 
       timer shall reset.  Upon completion of the TBR 
       period or the CarsBeforeReduction (CBR) parameter is 
       satisfied, whichever occurs first, the linear 
       reduction of the allowable gap from the Passage Time
       shall begin.
       <DescriptiveName> NTCIP-1202::ASC.phaseTimeBeforeReduction
       <DataConceptType> Data Element
       <Unit> second"
   REFERENCE
      "NEMA TS 2 Clause 3.5.3.1 and 3.5.3.2.1.b.(2)"
::= { phaseEntry 13 }

-- 2.1.2.14 PHASE CARS BEFORE REDUCTION PARAMETER

phaseCarsBeforeReduction   OBJECT-TYPE
   SYNTAX   INTEGER (0..255)
   ACCESS   read-write
   STATUS   mandatory
   DESCRIPTION
      "<Definition> Phase Cars Before Reduction (CBR) 
       Parameter (0-255 vehicles). When the phase is Green 
       and the sum of the cars waiting (vehicle actuations 
       during Yellow & Red intervals) on serviceable 
       conflicting phases equals or exceeds the CBR 
       parameter or the Time Before Reduction (TBR) 
       parameter is satisfied, whichever occurs first, the 
       linear reduction of the allowable gap from the 
       Passage Time shall begin.
       <DescriptiveName> NTCIP-1202::ASC.phaseCarsBeforeReduction
       <DataConceptType> Data Element
       <Unit> vehicle"
::= { phaseEntry 14 }

-- 2.1.2.15 PHASE TIME TO REDUCE PARAMETER

phaseTimeToReduce   OBJECT-TYPE
   SYNTAX   INTEGER (0..255)
   ACCESS   read-write
   STATUS   mandatory
   DESCRIPTION
      "<Definition> Phase Time To Reduce Parameter in 
       seconds (0-255 sec). This parameter shall control 
       the rate of reduction of the allowable gap between 
       the Passage Time and Minimum Gap setting.
       <DescriptiveName> NTCIP-1202::ASC.phaseTimeToReduce
       <DataConceptType> Data Element
       <Unit> second"
   REFERENCE
      "NEMA TS 2 Clause 3.5.3.1 and 3.5.3.2.1.b.(2)"
::= { phaseEntry 15 }


-- 2.1.2.16 PHASE REDUCE BY

phaseReduceBy   OBJECT-TYPE
   SYNTAX   INTEGER (0..255) 
   ACCESS   read-write
   STATUS   mandatory
   DESCRIPTION
      "<Definition> This object may be used for volume 
       density gap reduction as an alternate to the linear 
       reduction defined by NEMA TS 1 and TS 2.  It contains
       the tenths of seconds to reduce the gap by (0.0 - 
       25.5 seconds).  The frequency of reduction shall 
       produce the Minimum Gap after a time equal to the 
       ‘phaseTimeToReduce? object.
       <DescriptiveName> NTCIP-1202::ASC.phaseReduceBy
       <DataConceptType> Data Element
       <Unit> tenth second"
::= { phaseEntry 16 }

-- 2.1.2.17 PHASE MINIMUM GAP PARAMETER

phaseMinimumGap   OBJECT-TYPE
   SYNTAX   INTEGER (0..255)
   ACCESS   read-write
   STATUS   mandatory
   DESCRIPTION
      "<Definition> Phase Minimum Gap Parameter in tenth 
       seconds (0-25.5 sec). The reduction of the allowable 
       gap shall continue until the gap reaches a value 
       equal to or less than the minimum gap as set on the 
       Minimum Gap control after which the allowable gap 
       shall remain fixed at the values set on the Minimum 
       Gap control.
       <DescriptiveName> NTCIP-1202::ASC.phaseMinimumGap
       <DataConceptType> Data Element
       <Unit> tenth second"
   REFERENCE
      "NEMA TS 2 Clause 3.5.3.1 and 3.5.3.2.1.b.(2)"
::= { phaseEntry 17 }

-- 2.1.2.18 PHASE DYNAMIC MAX LIMIT

phaseDynamicMaxLimit   OBJECT-TYPE
   SYNTAX   INTEGER (0..255)
   ACCESS   read-write
   STATUS   mandatory
   DESCRIPTION
      "<Definition> This object shall determine either the 
       upper or lower limit of the running max in seconds 
       (0-255 sec) during dynamic max operation.

       The normal maximum (i.e. Max1, Max2, etc.) shall 
       determine the other limit as follows:

       When dynamicMaxLimit is larger than the normal 
       maximum, it shall become the upper limit.

       When dynamicMaxLimit is smaller than the normal 
       maximum, it shall become the lower limit.

       Setting dynamicMaxLimit greater than zero enables 
       dynamic max operation with the normal maximum used 
       as the initial maximum setting.  See dynamicMaxStep 
       for details on dynamic max operation.

       Maximum recall or a failed detector that is assigned 
       to the associated phase shall disable dynamic max 
       operation for the phase.
       <DescriptiveName> NTCIP-1202::ASC.phaseDynamicMaxLimit
       <DataConceptType> Data Element
       <Unit> second"
::= { phaseEntry 18 }

-- 2.1.2.19 PHASE DYNAMIC MAX STEP

phaseDynamicMaxStep   OBJECT-TYPE
   SYNTAX   INTEGER (0..255)
   ACCESS   read-write
   STATUS   mandatory
   DESCRIPTION
      "<Definition> This object shall determine the 
       automatic adjustment to the running max in tenth 
       seconds (0-25.5)

       When a phase maxes out twice in a row, and on each 
       successive max out thereafter, one dynamic max step 
       value shall be added to the running max until such 
       addition would mean the running max was greater than 
       the larger of normal max or dynamic max limit.

       When a phase gaps out twice in a row, and on each 
       successive gap out thereafter, one dynamic max step 
       value shall be subtracted from the running max until 
       such subtraction would mean the running max was less 
       than the smaller of the normal max or the dynamic max 
       limit.

       If a phase gaps out in one cycle and maxes out in 
       the next cycle, or vice versa, the running max will 
       not change.
       <DescriptiveName> NTCIP-1202::ASC.phaseDynamicMaxStep
       <DataConceptType> Data Element
       <Unit> tenth second"
::= { phaseEntry 19 }

-- 2.1.2.20  PHASE STARTUP

phaseStartup   OBJECT-TYPE
   SYNTAX   INTEGER { other (1),
                      phaseNotOn (2),
                      greenWalk (3),
                      greenNoWalk (4),
                      yellowChange (5),
                      redClear (6) }
   ACCESS   read-write
   STATUS   mandatory
   DESCRIPTION
      "<Definition> The Phase Startup parameter is an 
       enumerated integer which selects the startup state 
       for each phase after restoration of a defined power 
       interruption or activation of the external start 
       input. The following entries are defined:
          other: this phase is not enabled (phaseOptions 
             bit 0=0 or phaseRing=0) or initializes in a 
             state not defined by this standard.
          phaseNotOn: this phase initializes in a Red state 
             (the phase is not active and no intervals are 
             timing).
          greenWalk: this phase initializes at the 
             beginning of the minimum green and walk timing 
             intervals. 
          greenNoWalk: this phase initializes at the 
             beginning of the minimum green timing interval.
          yellowChange: this phase initializes at the 
             beginning of the Yellow Change interval.
          redClear: this phase initializes at the beginning 
             of the Red Clearance interval.
       <DescriptiveName> NTCIP-1202::ASC.phaseStartup
       <DataConceptType> Data Element"
   REFERENCE
      "NEMA TS 2 Clause 3.5.5.1 and 3.5.5.12"
::= { phaseEntry 20 }

-- 2.1.2.21 PHASE OPTIONS

phaseOptions   OBJECT-TYPE
   SYNTAX   INTEGER (0..65535)
   ACCESS   read-write
   STATUS   mandatory
   DESCRIPTION
      "<Definition> Optional phase functions ( 0 = False/
       Disabled, 1 = True/Enabled)
       Bit 15: AddedInitialCalculation - If set (1) the CU 
          shall compare counts from all associated 
          AddedInitial detectors and use the largest 
          count value for the calculations.  If clear (0) 
          the CU shall sum all associated AddedInitial 
          detector counts and use this sum for the 
          calculations.  The ability to modify the setting 
          of this bit is optional.

       Bit 14: Conditional Service Enable - in multi-ring 
          configurations when set to 1 causes a gapped/maxed 
          phase to conditionally service a preceding actuated
          vehicle phase when sufficient time remains before 
          max time out of the phase(s) not prepared to 
          terminate. Support is optional.
          REFERENCE  NEMA TS 2 Clause 3.5.3.9
       Bit 13: Actuated Rest In Walk - when set to 1 causes 
          an actuated phase to rest in Walk when there is no 
          serviceable conflicting call at the end of Walk 
          Timing. 
       Bit 12: Guaranteed Passage - when set to 1 enables 
          an actuated phase operating in volume density mode
          (using gap reduction) to retain the right of 
          way for the unexpired portion of the Passage 
          time following the decision to terminate the 
          green due to a reduced gap.  Support is optional
       Bit 11: Simultaneous Gap Disable - in multi-ring 
          configurations when set to 1 disables a gapped 
          out phase from reverting to the extensible 
          portion. Support is optional
          REFERENCE NEMA TS 2 Clause 3.5.5.3
       Bit 10: Dual Entry Phase - in multi-ring 
          configurations when set to 1 causes the phase to 
          become active upon entry into a concurrency group 
         (crossing a barrier) when no calls exist in its 
          ring within its concurrency group.
          REFERENCE NEMA TS 2 Clause 3.5.5.3
       Bit 9: Soft Vehicle Recall - when set to 1 causes a 
          call on a phase when all conflicting phases are 
          in green dwell or red dwell and there are no 
          serviceable conflicting calls.  Support is 
          optional.
       Bit 8: Ped. Recall - when set to 1 causes a recurring 
          pedestrian demand which shall function in the same 
          manner as an external pedestrian call except that 
          it shall not recycle the pedestrian service until a 
          conflicting phase is serviced
          REFERENCE NEMA TS 2 Clause 3.5.3.7
       Bit 7: Max Vehicle Recall - when set to 1 causes  a 
          call on a phase such that the timing of the Green 
          interval for that phase shall be extended to 
          Maximum Green time.
          REFERENCE NEMA TS 2 Clause 3.5.3.5
       Bit 6: Min. Vehicle Recall - when set to 1 causes 
          recurring demand for vehicle service on the phase 
          when that phase is not in its Green interval.
          REFERENCE NEMA TS 2 Clause 3.5.3.6
       Bit 5: Non Lock Detector Memory - when set to 0 will 
          cause the call to be locked at the beginning of 
          the yellow interval.  When set to 1 call locking 
          will depend on the detectorOptions object. 
          REFERENCE NEMA TS 2 Clause 3.5.3.4
       Bit 4: Non-Actuated 2 - when set to 1 causes a phase 
          to respond to the Call To Non-Actuated 2 input 
          (if present) or other method. Support is optional
          REFERENCE NEMA TS 2 Clause 3.5.5.5.8
       Bit 3: Non-Actuated 1 - when set to 1 causes a phase 
          to respond to the Call To Non-Actuated 1 input 
          (if present) or other method. Support is optional
          REFERENCE NEMA TS 2 Clause 3.5.5.5.8
       Bit 2: Automatic Flash Exit Phase - The CU shall 
          move immediately to the beginning of the phase(s) 
          programmed as Exit Phase(s) when Automatic Flash 
          terminates. Support is optional
          REFERENCE NEMA TS 2 Clause 3.9.1.2.1
       Bit 1: Automatic Flash Entry Phase - When Automatic 
          Flash is called, the CU shall service the Entry 
          Phase(s), clear to an All Red, then initiate 
          flashing operation. Support is optional.
          REFERENCE NEMA TS 2 Clause 3.9.1.2.1
       Bit 0: Enabled Phase - provide a means to define 
          whether this phase is used in the current 
          configuration. A disabled phase shall not provide 
          any outputs nor respond to any phase inputs. The 
          object phaseRing = 0 has the same effect.
       <DescriptiveName> NTCIP-1202::ASC.phaseOptions
       <DataConceptType> Data Element"
::= { phaseEntry 21 }

-- 2.1.2.22 PHASE RING PARAMETER

phaseRing   OBJECT-TYPE
   SYNTAX   INTEGER (0..255)
   ACCESS   read-write
   STATUS   mandatory
   DESCRIPTION
      "<Definition> Phase ring number (1..maxRings) that 
       identified the ring which contains the associated 
       phase. This value must not exceed the maxRings 
       object value. If the ring number is zero, the 
       phase is disabled (phaseOptions Bit 0 = 0 has the 
       same effect).
       <DescriptiveName> NTCIP-1202::ASC.phaseRing
       <DataConceptType> Data Element
       <Unit> ring"
::= { phaseEntry 22 }

-- 2.1.2.23 PHASE CONCURRENCY

phaseConcurrency   OBJECT-TYPE
   SYNTAX   OCTET STRING
   ACCESS   read-write
   STATUS   mandatory
   DESCRIPTION
      "<Definition> Each octet contains a phase number 
       (binary value) that may run concurrently with the 
       associated phase.  Phases that are contained in the 
       same ring may NOT run concurrently.
       <DescriptiveName> NTCIP-1202::ASC.phaseConcurrency
       <DataConceptType> Data Element"
::= { phaseEntry 23 }


-- 2.1.3 MAXIMUM PHASE GROUPS

maxPhaseGroups   OBJECT-TYPE
   SYNTAX   INTEGER (1..255)
   ACCESS   read-only
   STATUS   mandatory
   DESCRIPTION
      "<Definition> The Maximum Number of Phase Groups (8 
       Phases per group) this Actuated Controller Unit 
       supports. This value is equal to TRUNCATE 
       [(maxPhases + 7) / 8]. This object indicates the 
       maximum rows which shall appear in the 
       phaseStatusGroupTable and phaseControlGroupTable.
       <DescriptiveName> NTCIP-1202::ASC.maxPhaseGroups
       <DataConceptType> Data Element
       <Unit> group"
::= { phase 3 }

-- 2.1.4 PHASE STATUS GROUP TABLE

phaseStatusGroupTable   OBJECT-TYPE
   SYNTAX   SEQUENCE OF PhaseStatusGroupEntry
   ACCESS   not-accessible
   STATUS   mandatory
   DESCRIPTION
      "<Definition> A table containing Actuated Controller 
       Unit Phase Output (Red, Yellow, & Green) and Call 
       (vehicle & pedestrian) status in groups of eight 
       Phases. The number of rows in this table is equal to 
       the maxPhaseGroups object.
       <TableType> static
       <DescriptiveName> NTCIP-1202::ASC.phaseStatusGroupTable
       <DataConceptType> Entity Type"
::= { phase 4 }

phaseStatusGroupEntry   OBJECT-TYPE
   SYNTAX   PhaseStatusGroupEntry
   ACCESS   not-accessible
   STATUS   mandatory
   DESCRIPTION
      "<Definition> Red, Yellow, & Green Output Status and 
       Vehicle and Pedestrian Call for eight Actuated 
       Controller Unit Phases.
       <DescriptiveName> NTCIP-1202::ASC.phaseStatusGroupEntry
       <DataConceptType> Entity Type"
   INDEX   { phaseStatusGroupNumber }
::= { phaseStatusGroupTable 1 }


PhaseStatusGroupEntry ::= SEQUENCE { 
   phaseStatusGroupNumber       INTEGER,
   phaseStatusGroupReds         INTEGER,
   phaseStatusGroupYellows      INTEGER,
   phaseStatusGroupGreens       INTEGER,
   phaseStatusGroupDontWalks    INTEGER,
   phaseStatusGroupPedClears    INTEGER,
   phaseStatusGroupWalks        INTEGER,
   phaseStatusGroupVehCalls     INTEGER,
   phaseStatusGroupPedCalls     INTEGER,
   phaseStatusGroupPhaseOns     INTEGER,
   phaseStatusGroupPhaseNexts   INTEGER }

-- 2.1.4.1 PHASE STATUS GROUP NUMBER

phaseStatusGroupNumber   OBJECT-TYPE
   SYNTAX   INTEGER (1..255)
   ACCESS   read-only
   STATUS   mandatory
   DESCRIPTION
      "<Definition> The Phase StatusGroup number for objects
       in this row. This value shall not exceed the 
       maxPhaseGroups object value.
       <DescriptiveName> NTCIP-1202::ASC.phaseStatusGroupNumber
       <DataConceptType> Data Element
       <Unit> group"
::= { phaseStatusGroupEntry 1 }

-- 2.1.4.2 PHASE STATUS GROUP REDS

phaseStatusGroupReds   OBJECT-TYPE
   SYNTAX   INTEGER (0..255)
   ACCESS   read-only
   STATUS   mandatory
   DESCRIPTION
      "<Definition> Phase Red Output Status Mask, when a 
       bit = 1, the Phase Red is currently active. When a 
       bit = 0, the Phase Red is NOT currently active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupReds
       <DataConceptType> Data Element"
::= { phaseStatusGroupEntry 2 }


-- 2.1.4.3 PHASE STATUS GROUP YELLOWS

phaseStatusGroupYellows   OBJECT-TYPE
   SYNTAX   INTEGER (0..255)
   ACCESS   read-only
   STATUS   mandatory
   DESCRIPTION
      "<Definition> Phase Yellow Output Status Mask, when a 
       bit = 1, the Phase Yellow is currently active. When a 
       bit = 0, the Phase Yellow is NOT currently active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupYellows
       <DataConceptType> Data Element"
::= { phaseStatusGroupEntry 3 }

-- 2.1.4.4 PHASE STATUS GROUP GREENS

phaseStatusGroupGreens   OBJECT-TYPE
   SYNTAX   INTEGER (0..255)
   ACCESS   read-only
   STATUS   mandatory
   DESCRIPTION
      "<Definition> Phase Green Output Status Mask, when a 
       bit = 1, the Phase Green is currently active. When a 
       bit = 0, the Phase Green is NOT currently active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupGreens
       <DataConceptType> Data Element"
::= { phaseStatusGroupEntry 4 }


-- 2.1.4.5 PHASE STATUS GROUP DONT WALKS

phaseStatusGroupDontWalks   OBJECT-TYPE
   SYNTAX   INTEGER (0..255)
   ACCESS   read-only
   STATUS   mandatory
   DESCRIPTION
      "<Definition> Phase Dont Walk Output Status Mask, when 
       a bit = 1, the Phase Dont Walk is currently active. 
       When a bit = 0, the Phase Dont Walk is NOT currently 
       active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupDontWalks
       <DataConceptType> Data Element"
::= { phaseStatusGroupEntry 5 }

-- 2.1.4.6 PHASE STATUS GROUP PEDESTRIAN CLEARS

phaseStatusGroupPedClears   OBJECT-TYPE
   SYNTAX   INTEGER (0..255)
   ACCESS   read-only
   STATUS   mandatory
   DESCRIPTION
      "<Definition> Phase Ped Clear Output Status Mask, when 
        a bit = 1, the Phase Ped Clear is currently active. 
        When a bit = 0, the Phase Ped Clear is NOT currently 
        active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupPedClears
       <DataConceptType> Data Element"
::= { phaseStatusGroupEntry 6 }


-- 2.1.4.7 PHASE STATUS GROUP WALKS

phaseStatusGroupWalks   OBJECT-TYPE
   SYNTAX   INTEGER (0..255)
   ACCESS   read-only
   STATUS   mandatory
   DESCRIPTION
      "<Definition> Phase Walk Output Status Mask, when a 
       bit = 1, the Phase Walk is currently active. When a 
       bit = 0, the Phase Walk is NOT currently active.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupWalks
       <DataConceptType> Data Element"
::= { phaseStatusGroupEntry 7 }

-- 2.1.4.8 PHASE STATUS GROUP VEHICLE CALLS

phaseStatusGroupVehCalls   OBJECT-TYPE
   SYNTAX   INTEGER (0..255)
   ACCESS   read-only
   STATUS   mandatory
   DESCRIPTION
      "<Definition> Phase Vehicle Call Status Mask, when a 
       bit = 1, the Phase vehicle currently has a call for 
       service. When a bit = 0, the Phase vehicle currently 
       does NOT have a call for service.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupVehCalls
       <DataConceptType> Data Element"
::= { phaseStatusGroupEntry 8 }


-- 2.1.4.9 PHASE STATUS GROUP PEDESTRIAN CALLS

phaseStatusGroupPedCalls   OBJECT-TYPE
   SYNTAX   INTEGER (0..255)
   ACCESS   read-only
   STATUS   mandatory
   DESCRIPTION
      "<Definition> Phase Pedestrian Call Status Mask, when 
       a bit = 1, the  Phase pedestrian currently has a call 
       for service. When a bit = 0, the Phase pedestrian 
       currently does NOT have a call for service.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupPedCalls
       <DataConceptType> Data Element"
::= { phaseStatusGroupEntry 9 }

-- 2.1.4.10 PHASE STATUS GROUP PHASE ONS

phaseStatusGroupPhaseOns   OBJECT-TYPE
   SYNTAX   INTEGER (0..255)
   ACCESS   read-only
   STATUS   mandatory
   DESCRIPTION
      "<Definition> Phase On Status Mask, when a bit = 1, 
       the Phase is currently active. When a bit = 0, the 
       Phase currently is NOT active. The phase is ON 
       during the Green, Yellow, & Red Clearance intervals 
       of that phase. It shall be permissible for this 
       status to be True (bit=1) during the Red Dwell state.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupPhaseOns
       <DataConceptType> Data Element"
::= { phaseStatusGroupEntry 10 }

-- 2.1.4.11  PHASE STATUS GROUP PHASE NEXTS

phaseStatusGroupPhaseNexts   OBJECT-TYPE
   SYNTAX   INTEGER (0..255)
   ACCESS   read-only
   STATUS   mandatory
   DESCRIPTION
      "<Definition> Phase Next Status Mask, when a bit = 1, 
       the Phase currently is committed to be NEXT in 
       sequence & remains present until the phase becomes 
       active (On/Timing). When a bit = 0, the Phase 
       currently is NOT committed to be NEXT in sequence. 
       The phase next to be serviced shall be determined at 
       the end of the green interval of the terminating 
       phase; except that if the decision cannot be made at 
       the end of the Green interval, it shall not be made 
       until after the end of all Vehicle Change & Clearance 
       intervals.
          Bit 7: Phase # = (phaseStatusGroupNumber * 8)
          Bit 6: Phase # = (phaseStatusGroupNumber * 8) - 1
          Bit 5: Phase # = (phaseStatusGroupNumber * 8) - 2
          Bit 4: Phase # = (phaseStatusGroupNumber * 8) - 3
          Bit 3: Phase # = (phaseStatusGroupNumber * 8) - 4
          Bit 2: Phase # = (phaseStatusGroupNumber * 8) - 5
          Bit 1: Phase # = (phaseStatusGroupNumber * 8) - 6
          Bit 0: Phase # = (phaseStatusGroupNumber * 8) - 7
       <DescriptiveName> NTCIP-1202::ASC.phaseStatusGroupPhaseNexts
       <DataConceptType> Data Element"
::= { phaseStatusGroupEntry 11 }

-- 2.1.5 PHASE CONTROL TABLE

phaseControlGroupTable   OBJECT-TYPE
   SYNTAX   SEQUENCE OF PhaseControlGroupEntry
   ACCESS   not-accessible
   STATUS   mandatory
   DESCRIPTION
      "<Definition> A table containing Actuated Controller 
       Unit Phase Control in groups of eight phases. The 
       number of rows in this table is equal to the 
       maxPhaseGroups object.
       <TableType> static
       <DescriptiveName> NTCIP-1202::ASC.phaseControlGroupTable
       <DataConceptType> Entity Type
       <Unit> group"
::= { phase 5 }

phaseControlGroupEntry   OBJECT-TYPE
   SYNTAX   PhaseControlGroupEntry
   ACCESS   not-accessible
   STATUS   mandatory
   DESCRIPTION
      "<Definition> Phase Control for eight Actuated 
       Controller Unit phases.
       <DescriptiveName> NTCIP-1202::ASC.phaseControlGroupEntry
       <DataConceptType> Entity Type"

   INDEX   { phaseControlGroupNumber }
::= { phaseControlGroupTable 1 }

PhaseControlGroupEntry ::= SEQUENCE { 
   phaseControlGroupNumber      INTEGER,
   phaseControlGroupPhaseOmit   INTEGER,
   phaseControlGroupPedOmit     INTEGER,
   phaseControlGroupHold        INTEGER,
   phaseControlGroupForceOff    INTEGER,
   phaseControlGroupVehCall     INTEGER,
   phaseControlGroupPedCall     INTEGER }

-- 2.1.5.1 PHASE CONTROL GROUP NUMBER

phaseControlGroupNumber   OBJECT-TYPE
   SYNTAX   INTEGER (1..255)
   ACCESS   read-only
   STATUS   mandatory
   DESCRIPTION
      "<Definition> The Phase Control Group number for 
       objects in this row. This value shall not exceed the 
       maxPhaseGroups object value.
       <DescriptiveName> NTCIP-1202::ASC.phaseControlGroupNumber
       <DataConceptType> Data Element
       <Unit> group"
::= { phaseControlGroupEntry 1 }

-- 2.1.5.2 PHASE OMIT CONTROL

phaseControlGroupPhaseOmit   OBJECT-TYPE
   SYNTAX   INTEGER (0..255)
   ACCESS   read-write
   STATUS   mandatory
   DESCRIPTION
      "<Definition> This object is used to allow a remote 
       entity to omit phases from being serviced in the 
       device. When a bit = 1, the device shall activate 
       the System Phase Omit control for that phase. When a 
       bit = 0, the device shall not activate the System 
       Phase Omit control for that phase.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).
       <DescriptiveName> NTCIP-1202::ASC.phaseControlGroupPhaseOmit
       <DataConceptType> Data Element"
   REFERENCE
      "NEMA TS 2 Clause 3.5.3.11.2"
::= { phaseControlGroupEntry 2 }

-- 2.1.5.3 PEDESTRIAN OMIT CONTROL

phaseControlGroupPedOmit   OBJECT-TYPE
   SYNTAX   INTEGER (0..255)
   ACCESS   read-write
   STATUS   mandatory
   DESCRIPTION
      "<Definition> This object is used to allow a remote 
       entity to omit peds from being serviced in the 
       device. When a bit = 1, the device shall activate 
       the System Ped Omit control for that phase. When a 
       bit = 0, the device shall not activate the System 
       Ped Omit control for that phase.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).
       <DescriptiveName> NTCIP-1202::ASC.phaseControlGroupPedOmit
       <DataConceptType> Data Element"
   REFERENCE
      "NEMA TS 2 Clause 3.5.3.11.3"
::= { phaseControlGroupEntry 3 }

-- 2.1.5.4 PHASE HOLD CONTROL

phaseControlGroupHold   OBJECT-TYPE
   SYNTAX   INTEGER (0..255)
   ACCESS   read-write
   STATUS   mandatory
   DESCRIPTION
      "<Definition> This object is used to allow a remote 
       entity to hold phases in the device. When a bit = 1, 
       the device shall activate the System Phase Hold 
       control for that phase. When a bit = 0, the device 
       shall not activate the System Phase Hold control for 
       that phase.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).

       <DescriptiveName> NTCIP-1202::ASC.phaseControlGroupHold
       <DataConceptType> Data Element"
   REFERENCE
      "NEMA TS 2 Clause 3.5.3.11.1"
::= { phaseControlGroupEntry 4 }

-- 2.1.5.5 PHASE FORCE OFF CONTROL

phaseControlGroupForceOff   OBJECT-TYPE
   SYNTAX   INTEGER (0..255)
   ACCESS   read-write
   STATUS   mandatory
   DESCRIPTION
      "<Definition> This object is used to apply force offs 
       on a per phase basis. When a bit = 1, the device 
       shall activate the System Phase Force Off control 
       for that phase. When a bit = 0, the device shall not 
       activate the System Phase Force Off control for that 
       phase.  When the phase green terminates, the 
       associated bit shall be reset to 0.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).
       <DescriptiveName> NTCIP-1202::ASC.phaseControlGroupForceOff
       <DataConceptType> Data Element"
::= { phaseControlGroupEntry 5 }

-- 2.1.5.6 VEHICLE CALL CONTROL

phaseControlGroupVehCall   OBJECT-TYPE
   SYNTAX   INTEGER (0..255)
   ACCESS   read-write
   STATUS   mandatory
   DESCRIPTION
      "<Definition> This object is used to allow a remote 
       entity to place calls for vehicle service in the 
       device. When a bit = 1, the device shall place a 
       call for vehicle service on that phase. When a 
       bit = 0, the device shall not place a call for 
       vehicle service on that phase.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).
       <DescriptiveName> NTCIP-1202::ASC.phaseControlGroupVehCall
       <DataConceptType> Data Element"
::= { phaseControlGroupEntry 6 }

-- 2.1.5.7 PEDESTRIAN CALL CONTROL

phaseControlGroupPedCall   OBJECT-TYPE
   SYNTAX   INTEGER (0..255)
   ACCESS   read-write
   STATUS   mandatory
   DESCRIPTION
      "<Definition> This object is used to allow a remote 
       entity to place calls for ped service in the device. 
       When a bit = 1, the device shall place a call for ped 
       service on that phase. When a bit = 0, the device 
       shall not place a call for ped service on that phase.
          Bit 7: Phase # = (phaseControlGroupNumber * 8)
          Bit 6: Phase # = (phaseControlGroupNumber * 8) - 1
          Bit 5: Phase # = (phaseControlGroupNumber * 8) - 2
          Bit 4: Phase # = (phaseControlGroupNumber * 8) - 3
          Bit 3: Phase # = (phaseControlGroupNumber * 8) - 4
          Bit 2: Phase # = (phaseControlGroupNumber * 8) - 5
          Bit 1: Phase # = (phaseControlGroupNumber * 8) - 6
          Bit 0: Phase # = (phaseControlGroupNumber * 8) - 7
       The device shall reset this object to ZERO when in BACKUP 
       Mode. A write to this object shall reset the Backup timer 
       to ZERO (see unitBackupTime).
       <DescriptiveName> NTCIP-1202::ASC.phaseControlGroupPedCall
       <DataConceptType> Data Element"
::= { phaseControlGroupEntry 7 }

-- 2.2 DETECTOR PARAMETERS

detector OBJECT IDENTIFIER 
::= { asc 2 }

-- This defines a node for supporting detector objects.

-- 2.2.1 MAXIMUM VEHICLE DETECTORS

maxVehicleDetectors   OBJECT-TYPE
   SYNTAX   INTEGER (1..255)
   ACCESS   read-only
   STATUS   mandatory
   DESCRIPTION
      "<Definition> The Maximum Number of Vehicle Detectors 
       this Actuated Controller Unit supports. This object 
       indicates the maximum rows which shall appear in the 
       vehicleDetectorTable object.
       <DescriptiveName> NTCIP-1202::ASC.maxVehicleDetectors
       <DataConceptType> Data Element
       <Unit> detector"
::= { detector 1 }

-- 2.2.2 VEHICLE DETECTOR PARAMETER TABLE

vehicleDetectorTable   OBJECT-TYPE
   SYNTAX   SEQUENCE OF VehicleDetectorEntry
   ACCESS   not-accessible
   STATUS   mandatory
   DESCRIPTION
      "<Definition> A table containing Actuated Controller 
       Unit vehicle detector parameters. The number of rows 
       in this table is equal to the maxVehicleDetectors 
       object.
       <TableType> static
       <DescriptiveName> NTCIP-1202::ASC.vehicleDetectorTable
       <DataConceptType> Entity Type"
::= { detector 2 }

vehicleDetectorEntry   OBJECT-TYPE
   SYNTAX   VehicleDetectorEntry
   ACCESS   not-accessible
   STATUS   mandatory
   DESCRIPTION
      "<Definition> Parameters for a specific Actuated 
       Controller Unit detector.
       <DescriptiveName> NTCIP-1202::ASC.vehicleDetectorEntry
       <DataConceptType> Entity Type"
   INDEX   { vehicleDetectorNumber }
::= { vehicleDetectorTable 1 }

VehicleDetectorEntry ::= SEQUENCE {
   vehicleDetectorNumber           INTEGER,
   vehicleDetectorOptions          INTEGER,
   vehicleDetectorCallPhase        INTEGER,
   vehicleDetectorSwitchPhase      INTEGER,
   vehicleDetectorDelay            INTEGER,
   vehicleDetectorExtend           INTEGER,
   vehicleDetectorQueueLimit       INTEGER,
   vehicleDetectorNoActivity       INTEGER,
   vehicleDetectorMaxPresence      INTEGER,
   vehicleDetectorErraticCounts    INTEGER,
   vehicleDetectorFailTime         INTEGER,
   vehicleDetectorAlarms           INTEGER,
   vehicleDetectorReportedAlarms   INTEGER,
   vehicleDetectorReset            INTEGER }

-- 2.2.2.1 VEHICLE DETECTOR NUMBER

vehicleDetectorNumber   OBJECT-TYPE
   SYNTAX   INTEGER (1..255)
   ACCESS   read-only
   STATUS   mandatory
   DESCRIPTION
      "<Definition> The vehicle detector number for objects 
       in this row. The value shall not exceed the 
       maxVehicleDetectors object value.
       <DescriptiveName> NTCIP-1202::ASC.vehicleDetectorNumber
       <DataConceptType> Data Element
       <Unit> detector"
::= { vehicleDetectorEntry 1 }

-- 2.2.2.2 VEHICLE DETECTOR OPTIONS PARAMETER

vehicleDetectorOptions   OBJECT-TYPE
   SYNTAX   INTEGER (0..255)
   ACCESS   read-write
   STATUS   mandatory
   DESCRIPTION
      "<Definition> Vehicle Detector Options Parameter as 
       follows (0=Disabled, 1=Enabled):
          Bit 7: Call - if Enabled, the CU shall place 
             a demand for vehicular service on the assigned 
             phase when the phase is not timing the green 
             interval and an actuation is present.
          Bit 6: Queue - if Enabled, the CU shall extend 
             the green interval of the assigned phase until a 
             gap occurs (no actuation) or until the green 
             has been active longer than the 
             vehicleDetectorQueueLimit time. 
             This is optional.
          Bit 5: AddedInitial - if Enabled, the CU shall
             accumulate detector actuation counts for use in 
             the added initial calculations. Counts shall be 
             accumulated from the beginning of the yellow 
             interval to the beginning of the green interval.
          Bit 4: Passage - if Enabled, the CU shall maintain
             a reset to the associated phase passage timer 
             for the duration of the detector actuation when 
             the phase is green.
          Bit 3: Red Lock Call - if Enabled, the detector
             will lock a call to the assigned phase if an 
             actuation occurs while the phase is not timing 
             Green or Yellow. This mode is optional.
          Bit 2: Yellow Lock Call - if Enabled, the detector
             will lock a call to the assigned phase if an 
             actuation occurs while the phase is not timing 
             Green.
          Bit 1: Occupancy Detector - if Enabled, the
             detector collects data for the associated 
             detector occupancy object(s).  This capability 
             may not be supported on all detector inputs to 
             a device.
          Bit 0: Volume Detector - if Enabled, the detector
             collects data for the associated detector 
             volume object(s). This capability may not be 
             supported on all detector inputs to a device.
       A SET of both bits 2 & 3 = 1 shall result in bit 2=1 and 
       bit 3=0.
       <DescriptiveName> NTCIP-1202::ASC.vehicleDetectorOptions
       <DataConceptType> Data Element"
::= { vehicleDetectorEntry 2}

-- Note: { vehicleDetectorEntry 3} is not used.


-- 2.2.2.3 VEHICLE DETECTOR CALL PHASE PARAMETER

vehicleDetectorCallPhase   OBJECT-TYPE
   SYNTAX   INTEGER (0..255)
   ACCESS   read-write
   STATUS   mandatory
   DESCRIPTION
      "<Definition> This object contains assigned phase 
       number for the detector input associated with this 
       row.  The associated detector call capability is 
       enabled when this object is set to a non-zero value. 
       The value shall not exceed the value of maxPhases.
       <DescriptiveName> NTCIP-1202::ASC.vehicleDetectorCallPhase
       <DataConceptType> Data Element
       <Unit> phase"
   REFERENCE
      "NEMA TS 2 Clause 3.5.5.5.4 and 3.5.5.5.5" 
::= { vehicleDetectorEntry 4 }

-- 2.2.2.4 VEHICLE DETECTOR SWITCH PHASE PARAMETER

vehicleDetectorSwitchPhase   OBJECT-TYPE
   SYNTAX   INTEGER (0..255)
   ACCESS   read-write
   STATUS   mandatory
   DESCRIPTION
      "<Definition> Detector Switch Phase Parameter (i.e., 
       Phase Number). The phase to which a vehicle detector 
       actuation shall be switched when the assigned phase 
       is Yellow or Red and the Switch Phase is Green.
       <DescriptiveName> NTCIP-1202::ASC.vehicleDetectorSwitchPhase
       <DataConceptType> Data Element
       <Unit> phase"
   REFERENCE
      "NEMA TS 2 Clause 3.5.5.5.4.c"
::= { vehicleDetectorEntry 5 }

-- 2.2.2.5 VEHICLE DETECTOR DELAY PARAMETER

vehicleDetectorDelay   OBJECT-TYPE
   SYNTAX   INTEGER (0..65535)
   ACCESS   read-write
   STATUS   mandatory
   DESCRIPTION
      "<Definition> Detector Delay Parameter in tenth 
       seconds (0?255.0 sec). The period a detector 
       actuation (input recognition) shall be delayed when 
       the phase is not Green.
       <DescriptiveName> NTCIP-1202::ASC.vehicleDetectorDelay
       <DataConceptType> Data Element
       <Unit> tenth second"
   REFERENCE
      "NEMA TS 2 Clause 3.5.5.5.4.a"
::= { vehicleDetectorEntry 6 }

-- 2.2.2.6 VEHICLE DETECTOR EXTEND PARAMETER

vehicleDetectorExtend   OBJECT-TYPE
   SYNTAX   INTEGER (0..255)
   ACCESS   read-write
   STATUS   mandatory
   DESCRIPTION
      "<Definition> Detector Extend Parameter in tenth 
       seconds (0?25.5 sec). The period a vehicle detector 
       actuation (input duration) shall be extended from the 
       point of termination , when the phase is Green.
       <DescriptiveName> NTCIP-1202::ASC.vehicleDetectorExtend
       <DataConceptType> Data Element
       <Unit> tenth second"
   REFERENCE
      "NEMA TS 2 Clause 3.5.5.5.4.b"
::= { vehicleDetectorEntry 7 }

-- 2.2.2.7 VEHICLE DETECTOR QUEUE LIMIT

vehicleDetectorQueueLimit   OBJECT-TYPE
   SYNTAX   INTEGER (0..255)
   ACCESS   read-write
   STATUS   mandatory
   DESCRIPTION
      "<Definition> Detector Queue Limit parameter in 
       seconds (0-255 sec). The length of time that an 
       actuation from a queue detector may continue into 
       the phase green.  This time begins when the phase 
       becomes green and when it expires any associated 
       detector inputs shall be ignored.  This time may be 
       shorter due to other overriding device parameters 
       (i.e. Maximum time, Force Off’s, ...).
       <DescriptiveName> NTCIP-1202::ASC.vehicleDetectorQueueLimit
       <DataConceptType> Data Element
       <Unit> second"
::= { vehicleDetectorEntry 8 }

-- 2.2.2.8 VEHICLE DETECTOR NO ACTIVITY PARAMETER

vehicleDetectorNoActivity   OBJECT-TYPE
   SYNTAX   INTEGER (0..255)
   ACCESS   read-write
   STATUS   mandatory
   DESCRIPTION
      "<Definition> Detector No Activity diagnostic 
       Parameter in minutes (0?255 min.) . If an active 
       detector does not exhibit an actuation in the 
       specified period, it is considered a fault by the 
       diagnostics and the detector is classified as Failed. 
       A value of 0 for this object shall disable this 
       diagnostic for this detector.
       <DescriptiveName> NTCIP-1202::ASC.vehicleDetectorNoActivity
       <DataConceptType> Data Element
       <Unit> minute"
   REFERENCE
      "NEMA TS 2 Clause 3.9.3.1.4.1"
::= { vehicleDetectorEntry 9 }

-- 2.2.2.9 VEHICLE DETECTOR MAXIMUM PRESENCE PARAMETER

vehicleDetectorMaxPresence   OBJECT-TYPE
   SYNTAX   INTEGER (0..255)
   ACCESS   read-write
   STATUS   mandatory
   DESCRIPTION
      "<Definition> Detector Maximum Presence diagnostic 
       Parameter in minutes (0-255 min.). If an active 
       detector exhibits continuous detection for too long 
       a period, it is considered a fault by the diagnostics 
       and the detector is classified as Failed. A value of 
       0 for this object shall disable this diagnostic for 
       this detector.
       <DescriptiveName> NTCIP-1202::ASC.vehicleDetectorMaxPresence
       <DataConceptType> Data Element
       <Unit> minute"
   REFERENCE
      "NEMA TS 2 Clause 3.9.3.1.4.2"
::= { vehicleDetectorEntry 10 }

-- 2.2.2.10 VEHICLE DETECTOR ERRATIC COUNTS PARAMETER

vehicleDetectorErraticCounts   OBJECT-TYPE
   SYNTAX   INTEGER (0..255)
   ACCESS   read-write
   STATUS   mandatory
   DESCRIPTION
      "<Definition> Detector Erratic Counts diagnostic 
       Parameter in counts/minute (0-255 cpm). If an active 
       detector exhibits excessive actuations, it is 
       considered a fault by the diagnostics and the 
       detector is classified as Failed. A value of 0 for 
       this object shall disable this diagnostic for this 
       detector.
       <DescriptiveName> NTCIP-1202::ASC.vehicleDetectorErraticCounts
       <DataConceptType> Data Element
       <Unit> count"
   REFERENCE
      "NEMA TS 2 Clause 3.9.3.1.4.3"
::= { vehicleDetectorEntry 11 }

-- 2.2.2.11 VEHICLE DETECTOR FAIL TIME PARAMETER

vehicleDetectorFailTime   OBJECT-TYPE
   SYNTAX   INTEGER (0..255)
   ACCESS   read-write
   STATUS   mandatory
   DESCRIPTION
      "<Definition> Detector Fail Time in seconds (0..255 sec). 
       If a detector diagnostic indicates that the 
       associated detector input is failed, then a call 
       shall be placed on the associated phase during all 
       non-green intervals. When each green interval begins 
       the call shall be maintained for the length of time 
       specified by this object and then removed. If the 
       value of this object equals the maximum value (255) 
       then a constant call shall be placed on the 
       associated phase (max recall). If the value of this 
       object equals zero then no call shall be placed on 
       the associated phase for any interval (no recall). 
       Compliant devices may support a limited capability 
       for this object (i.e. only max recall or max recall 
       and no recall). At a minimum the max recall setting 
       must be supported.
       <DescriptiveName> NTCIP-1202::ASC.vehicleDetectorFailTime
       <DataConceptType> Data Element
       <Unit> second"
::= { vehicleDetectorEntry 12 }

-- 2.2.2.12 VEHICLE DETECTOR ALARMS

vehicleDetectorAlarms   OBJECT-TYPE
   SYNTAX   INTEGER (0..255)
   ACCESS   read-only
   STATUS   mandatory
   DESCRIPTION
      "<Definition> This object shall return indications of 
       detector alarms. Detector Alarms are indicated as 
       follows:
          Bit 7: Other Fault - The detector has failed due 
             to some other cause.
          Bit 6: Reserved.
          Bit 5: Reserved.
          Bit 4: Configuration Fault - Detector is assigned 
             but is not supported.
          Bit 3: Communications Fault - Communications to 
             the device (if present) have failed.
          Bit 2: Erratic Output Fault - This detector has 
             been flagged as non-operational due to erratic 
             outputs (excessive counts) by the CU detector 
             diagnostic.
          Bit 1: Max Presence Fault - This detector has been 
             flagged as non-operational due to a presence 
             indicator that exceeded the maximum expected 
             time by the CU detector diagnostic.
          Bit 0: No Activity Fault - This detector has been 
             flagged as non-operational due to lower than 
             expected activity by the CU detector diagnostic.
       Once set a bit shall maintain its state as long as the 
       condition exists. The bit shall clear when the condition 
       no longer exists.
       <DescriptiveName> NTCIP-1202::ASC.vehicleDetectorAlarms
       <DataConceptType> Data Element"
::= { vehicleDetectorEntry  13 }


-- 2.2.2.13 VEHICLE DETECTOR REPORTED ALARMS

vehicleDetectorReportedAlarms   OBJECT-TYPE
   SYNTAX   INTEGER (0..255)
   ACCESS   read-only
   STATUS   mandatory
   DESCRIPTION
      "<Definition> This object shall return detector device 
       reported alarms (via some communications mechanism). 
       Inductive Loop Detector Alarms are indicated as 
       follows:
          Bit 7: Reserved.
          Bit 6: Reserved.
          Bit 5: Reserved.
          Bit 4: Excessive Change Fault - This detector has 
             been flagged as non-operational due to an 
             inductance change that exceeded expected values.
          Bit 3: Shorted Loop Fault - This detector has been 
             flagged as non-operational due to a shorted loop 
             wire.
          Bit 2: Open Loop Fault - This detector has been 
             flagged as non-operational due to an open loop 
             (broken wire).
          Bit 1: Watchdog Fault - This detector has been 
             flagged as non-operational due to a watchdog 
             error.
          Bit 0: Other - This detector has been flagged as 
             non-operational due to some other error.
       Once set a bit shall maintain its state as long as 
       the condition exists.  The bit shall clear when the 
       condition no longer exists.
       <DescriptiveName> NTCIP-1202::ASC.vehicleDetectorReportedAlarms
       <DataConceptType> Data Element"
::= { vehicleDetectorEntry  14 }

-- 2.2.2.14 VEHICLE DETECTOR RESET

vehicleDetectorReset   OBJECT-TYPE
   SYNTAX   INTEGER (0..1)
   ACCESS   read-write
   STATUS   mandatory
   DESCRIPTION
      "<Definition> This object when set to TRUE (one) 
       shall cause the CU to command the associated detector 
       to reset.  This object shall automatically return to 
       FALSE (zero)  after the CU has issued the reset 
       command.

       NOTE: this may affect other detector (detector 
       channels) that are physically attached to a common 
       reset line.
       <DescriptiveName> NTCIP-1202::ASC.vehicleDetectorReset
       <DataConceptType> Data Element"
::= { vehicleDetectorEntry 15 }

-- 2.2.3 MAXIMUM VEHICLE DETECTOR STATUS GROUPS

maxVehicleDetectorStatusGroups   OBJECT-TYPE
   SYNTAX   INTEGER (1..255)
   ACCESS   read-only
   STATUS   mandatory
   DESCRIPTION
      "<Definition> The maximum number of detector status 
       groups (8 detectors per group) this device supports. 
       This value is equal to TRUNCATE 
       [(maxVehicleDetectors + 7 ) / 8].  This object 
       indicates the maximum number of rows which shall 
       appear in the vehicleDetectorStatusGroupTable object.
       <DescriptiveName> NTCIP-1202::ASC.maxVehicleDetectorStatusGroups
       <DataConceptType> Data Element
       <Unit> group"
::= { detector 3 }

-- 2.2.4 VEHICLE DETECTOR STATUS GROUP TABLE

vehicleDetectorStatusGroupTable   OBJECT-TYPE
   SYNTAX   SEQUENCE OF VehicleDetectorStatusGroupEntry
   ACCESS   not-accessible
   STATUS   mandatory
   DESCRIPTION
      "<Definition> A table containing detector status in 
       groups of eight detectors. The number of rows in this 
       table is equal to the maxVehicleDetectorStatusGroups 
       object.
       <TableType> static
       <DescriptiveName> NTCIP-1202::ASC.vehicleDetectorStatusGroupTable
       <DataConceptType> Entity Type"
::= { detector 4 }

vehicleDetectorStatusGroupEntry   OBJECT-TYPE
   SYNTAX   VehicleDetectorStatusGroupEntry
   ACCESS   not-accessible
   STATUS   mandatory
   DESCRIPTION
      "<Definition> A group (row) of detector status.
       <DescriptiveName> NTCIP-1202::ASC.vehicleDetectorStatusGroupEntry
       <DataConceptType> Entity Type"
   INDEX  { vehicleDetectorStatusGroupNumber }
::= { vehicleDetectorStatusGroupTable  1 }

VehicleDetectorStatusGroupEntry ::= SEQUENCE {
   vehicleDetectorStatusGroupNumber   INTEGER,
   vehicleDetectorStatusGroupActive   INTEGER,
   vehicleDetectorStatusGroupAlarms   INTEGER }

-- 2.2.4.1 DETECTOR STATUS GROUP NUMBER

vehicleDetectorStatusGroupNumber   OBJECT-TYPE
   SYNTAX   INTEGER (1..255)
   ACCESS   read-only
   STATUS   mandatory
   DESCRIPTION
      "<Definition> The detector status group number for 
       objects in this row. This value shall not exceed the 
       maxVehicleDetectorStatusGroups object value.
       <DescriptiveName> NTCIP-1202::ASC.vehicleDetectorStatusGroupNumber
       <DataConceptType> Data Element
       <Unit> group"
::= { vehicleDetectorStatusGroupEntry 1 }

-- 2.2.4.2 DETECTOR STATUS GROUP ACTIVE

vehicleDetectorStatusGroupActive   OBJECT-TYPE
   SYNTAX   INTEGER (0..255)
   ACCESS   read-only
   STATUS   mandatory
   DESCRIPTION
      "<Definition> This object shall return the detection 
       status of each detector associated with the group. 
       Each detector shall be represented as ON (detect) or 
       OFF (no-detect) by individual bits in this object.  
       If a detector is ON then the associated bit shall be 
       set (1).  If a detector is OFF then the associated 
       bit shall be clear (0).
          Bit 7: Det # = ( vehicleDetectorStatusGroupNumber * 8)
          Bit 6: Det # = ( vehicleDetectorStatusGroupNumber * 8) - 1
          Bit 5: Det # = ( vehicleDetectorStatusGroupNumber * 8) - 2
          Bit 4: Det # = ( vehicleDetectorStatusGroupNumber * 8) - 3
          Bit 3: Det # = ( vehicleDetectorStatusGroupNumber * 8) - 4
          Bit 2: Det # = ( vehicleDetectorStatusGroupNumber * 8) - 5
          Bit 1: Det # = ( vehicleDetectorStatusGroupNumber * 8) - 6
          Bit 0: Det # = ( vehicleDetectorStatusGroupNumber * 8) - 7
       <DescriptiveName> NTCIP-1202::ASC.vehicleDetectorStatusGroupActive
       <DataConceptType> Data Element"
::= { vehicleDetectorStatusGroupEntry 2 }

-- 2.2.4.3 DETECTOR ALARM STATUS

vehicleDetectorStatusGroupAlarms   OBJECT-TYPE
   SYNTAX   INTEGER (0..255)
   ACCESS   read-only
   STATUS   mandatory
   DESCRIPTION
      "<Definition> This object shall return the alarm status 
       of the detectors associated with the group.  Each 
       detector alarm status shall be represented as ON or 
       OFF by individual bits in this object.  If any 
       detector alarm (defined in the vehicleDetectorAlarm 
       object) is active the associated bit shall be 
       set (1).  If a detector alarm is not active the 
       associated bit shall be clear (0).
          Bit 7: Det # = ( vehicleDetectorStatusGroupNumber * 8)
          Bit 6: Det # = ( vehicleDetectorStatusGroupNumber * 8) - 1
          Bit 5: Det # = ( vehicleDetectorStatusGroupNumber * 8) - 2
          Bit 4: Det # = ( vehicleDetectorStatusGroupNumber * 8) - 3
          Bit 3: Det # = ( vehicleDetectorStatusGroupNumber * 8) - 4
          Bit 2: Det # = ( vehicleDetectorStatusGroupNumber * 8) - 5
          Bit 1: Det # = ( vehicleDetectorStatusGroupNumber * 8) - 6
          Bit 0: Det # = ( vehicleDetectorStatusGroupNumber * 8) - 7
       <DescriptiveName> NTCIP-1202::ASC.vehicleDetectorStatusGroupAlarms
       <DataConceptType> Data Element"
::= { vehicleDetectorStatusGroupEntry 3 }

-- 2.2.5 VOLUME / OCCUPANCY REPORT 

volumeOccupancyReport   OBJECT IDENTIFIER 
::= { detector 5 }

-- This node contains the objects necessary to support volume / 
-- occupancy reporting.

-- 2.2.5.1 VOLUME / OCCUPANCY SEQUENCE

volumeOccupancySequence   OBJECT-TYPE
   SYNTAX   INTEGER (0..255)
   ACCESS   read-only
   STATUS   mandatory
   DESCRIPTION
      "<Definition> This object defines a Sequence Number 
       for Volume/Occupancy data collection.  This object 
       is used to detect duplicate or missing reports.  The 
       value cycles within the limits of 0 to 255.  This 
       object is incremented by one at the expiration of the 
       volumeOccupancyPeriod time.
       <DescriptiveName> NTCIP-1202::ASC.volumeOccupancySequence
       <DataConceptType> Data Element
       <Unit> sequence"
::= { volumeOccupancyReport 1 }

-- 2.2.5.2 VOLUME / OCCUPANCY PERIOD

volumeOccupancyPeriod   OBJECT-TYPE
   SYNTAX   INTEGER (0..255)
   ACCESS   read-write
   STATUS   mandatory
   DESCRIPTION
      "<Definition> This object defines the number of 
       seconds (0-255 sec) that comprise the Volume/Occupancy 
       collection period.  When the collection period 
       expires the device shall increment the 
       volumeOccupancySequence,  update the 
       volumeOccupancyTable entries and reset the volume 
       occupancy timer.
       <DescriptiveName> NTCIP-1202::ASC.volumeOccupancyPeriod
       <DataConceptType> Data Element
       <Unit> second"
::= { volumeOccupancyReport 2 }

-- 2.2.5.3 ACTIVE VOLUME / OCCUPANCY DETECTORS

activeVolumeOccupancyDetectors   OBJECT-TYPE
   SYNTAX   INTEGER (0..255)
   ACCESS   read-only
   STATUS   mandatory
   DESCRIPTION
      "<Definition> The number of detectors in this device. 
       This object indicates how many rows are in the 
       volumeOccupancyTable object. There shall be a row 
       for every detector that is collecting volume or 
       occupancy data (refer to detectorOptions in the 
       detectorTable).
       <DescriptiveName> NTCIP-1202::ASC.activeVolumeOccupancyDetectors
       <DataConceptType> Data Element
       <Unit> detector"
::= { volumeOccupancyReport 3 }

-- 2.2.5.4 VOLUME / OCCUPANCY TABLE

volumeOccupancyTable   OBJECT-TYPE
   SYNTAX   SEQUENCE OF VolumeOccupancyEntry
   ACCESS   not-accessible
   STATUS   mandatory
   DESCRIPTION
      "<Definition> A table containing Detector Volume and 
       Occupancy data collected. The number of rows in this 
       table is equal to the activeVolumeOccupancyDetectors 
       object.
       <TableType> static
       <DescriptiveName> NTCIP-1202::ASC.volumeOccupancyTable
       <DataConceptType> Entity Type"
::= { volumeOccupancyReport 4 }

volumeOccupancyEntry   OBJECT-TYPE
   SYNTAX   VolumeOccupancyEntry
   ACCESS   not-accessible
   STATUS   mandatory
   DESCRIPTION
      "<Definition> The Volume and Occupancy data collected 
       for one of the detectors in the device.
       <DescriptiveName> NTCIP-1202::ASC.volumeOccupancyEntry
       <DataConceptType> Entity Type"
   INDEX   { vehicleDetectorNumber }
::= { volumeOccupancyTable 1 }

VolumeOccupancyEntry ::= SEQUENCE { 
   detectorVolume      INTEGER,
   detectorOccupancy   INTEGER }


-- 2.2.5.4.1 VOLUME DATA

detectorVolume   OBJECT-TYPE
   SYNTAX   INTEGER (0..255)
   ACCESS   read-only
   STATUS   mandatory
   DESCRIPTION
      "<Definition> Detector Volume data collected over the 
       volumeOccupancyPeriod. This value shall range from 
       0 to 254 indicating the volume of traffic crossing 
       the associated detectorNumber during the collection 
       period. 

       The value 255 shall indicate volume overflow.
       <DescriptiveName> NTCIP-1202::ASC.detectorVolume
       <DataConceptType> Data Element
       <Unit> volume"
::= { volumeOccupancyEntry 1 }

-- 2.2.5.4.2 OCCUPANCY DATA

detectorOccupancy   OBJECT-TYPE
   SYNTAX   INTEGER (0..255)
   ACCESS   read-only
   STATUS   mandatory
   DESCRIPTION
      "<Definition> Detector Occupancy as a percentage of the
       volumeOccupancyPeriod over which the data was collected
       or Detector Unit Diagnostic Information.  The value of
       the object shall indicate occupancy or detector diagnostic
       information as follows:
          Range   Meaning
          0-200   Detector Occupancy in 0.5% Increments
        201-209   Reserved
          210     Max Presence Fault
          211     No Activity Fault
          212     Open loop Fault
          213     Shorted loop Fault
          214     Excessive Change Fault
          215     Reserved
          216     Watchdog Fault
          217     Erratic Output Fault
        218-255   Reserved 

       Faults shall be indicated for all collection periods 
       during which a fault is detected if either occupancy 
       data or volume data is being collected.  The highest 
       numbered fault shall be presented if more than one 
       fault is active (i.e. indicate OpenLoop rather than 
       NoActivity).
       <DescriptiveName> NTCIP-1202::ASC.detectorOccupancy
       <DataConceptType> Data Element
       <Unit> occupancy"
::= { volumeOccupancyEntry 2 }

-- 2.2.6 MAXIMUM PEDESTRIAN DETECTORS

maxPedestrianDetectors OBJECT-TYPE
   SYNTAX   INTEGER (1..255)
   ACCESS   read-only
   STATUS   mandatory
   DESCRIPTION
      "<Definition> The Maximum Number of Pedestrian 
       Detectors this Actuated Controller Unit supports. 
       This object indicates the maximum rows which shall 
       appear in the pedestrianDetectorTable object.
       <DescriptiveName> NTCIP-1202::ASC.maxVehicleDetectors
       <DataConceptType> Data Element
       <Unit> detector"
::= { detector 6 }

-- 2.2.7 PEDESTRIAN DETECTOR PARAMETER TABLE

pedestrianDetectorTable   OBJECT-TYPE
   SYNTAX   SEQUENCE OF PedestrianDetectorEntry
   ACCESS   not-accessible
   STATUS   mandatory
   DESCRIPTION
      "<Definition> A table containing Actuated Controller 
       Unit pedestrian detector parameters. The number of 
       rows in this table is equal to the 
       maxPedestrianDetectors object.
       <TableType> static
       <DescriptiveName> NTCIP-1202::ASC.pedestrianDetectorTable
       <DataConceptType> Entity Type"
::= { detector 7 }

pedestrianDetectorEntry   OBJECT-TYPE
   SYNTAX   PedestrianDetectorEntry
   ACCESS   not-accessible
   STATUS   mandatory
   DESCRIPTION
      "<Definition> Parameters for a specific Actuated 
       Controller Unit pedestrian detector.
       <DescriptiveName> NTCIP-1202::ASC.pedestrianDetectorEntry
       <DataConceptType> Entity Type"
   INDEX   { pedestrianDetectorNumber }
::= { pedestrianDetectorTable 1 }

PedestrianDetectorEntry ::= SEQUENCE {
   pedestrianDetectorNumber          INTEGER,
   pedestrianDetectorCallPhase       INTEGER,
   pedestrianDetectorNoActivity      INTEGER,
   pedestrianDetectorMaxPresence     INTEGER,
   pedestrianDetectorErraticCounts   INTEGER,
   pedestrianDetectorAlarms          INTEGER }


-- 2.2.7.1 PEDESTRIAN DETECTOR NUMBER

pedestrianDetectorNumber   OBJECT-TYPE
   SYNTAX   INTEGER (1..255)
   ACCESS   read-only
   STATUS   mandatory
   DESCRIPTION
      "<Definition> The pedestrianDetector number for 
       objects in this row. The value shall not exceed the 
       maxPedestrianDetectors object value.
       <DescriptiveName> NTCIP-1202::ASC.pedestrianDetectorNumber
       <DataConceptType> Data Element
       <Unit> detector"
::= { pedestrianDetectorEntry 1 }

-- 2.2.7.2 PEDESTRIAN DETECTOR CALL PHASE PARAMETER

pedestrianDetectorCallPhase   OBJECT-TYPE
   SYNTAX   INTEGER (0..255)
   ACCESS   read-write
   STATUS   mandatory
   DESCRIPTION
      "<Definition> This object contains assigned phase 
       number for the pedestrian detector input associated 
       with this row.  The associated detector call 
       capability is enabled when this object is set to a 
       non-zero value. The value shall not exceed the 
       value of maxPhases.
       <DescriptiveName> NTCIP-1202::ASC.pedestrianDetectorCallPhase
       <DataConceptType> Data Element
       <Unit> phase"
::= { pedestrianDetectorEntry 2 }

-- 2.2.7.3 PEDESTRIAN DETECTOR NO ACTIVITY PARAMETER

pedestrianDetectorNoActivity   OBJECT-TYPE
   SYNTAX   INTEGER (0..255)
   ACCESS   read-write
   STATUS   mandatory
   DESCRIPTION
      "<Definition> Pedestrian Detector No Activity 
       diagnostic Parameter in minutes (0?255 min.) . If an 
       active detector does not exhibit an actuation in the 
       specified period, it is considered a fault by the 
       diagnostics and the detector is classified as Failed. 
       A value of 0 for this object shall disable this 
       diagnostic for this detector.
       <DescriptiveName> NTCIP-1202::ASC.pedestrianDetectorNoActivity
       <DataConceptType> Data Element
       <Unit> minute"
   REFERENCE
      "NEMA TS 2 Clause 3.9.3.1.4.1"
::= { pedestrianDetectorEntry 3 }

-- 2.2.7.4 PEDESTRIAN DETECTOR MAXIMUM PRESENCE PARAMETER

pedestrianDetectorMaxPresence   OBJECT-TYPE
   SYNTAX   INTEGER (0..255)
   ACCESS   read-write
   STATUS   mandatory
   DESCRIPTION
      "<Definition> Pedestrian Detector Maximum Presence 
       diagnostic Parameter in minutes (0-255 min.). If an 
       active detector exhibits continuous detection for 
       too long a period, it is considered a fault by the 
       diagnostics and the detector is classified as Failed. 
       A value of 0 for this object shall disable this 
       diagnostic for this detector.
       <DescriptiveName> NTCIP-1202::ASC.pedestrianDetectorMaxPresence
       <DataConceptType> Data Element
       <Unit> minute"
   REFERENCE
      "NEMA TS 2 Clause 3.9.3.1.4.2"
::= { pedestrianDetectorEntry 4 }

-- 2.2.7.5 PEDESTRIAN DETECTOR ERRATIC COUNTS PARAMETER

pedestrianDetectorErraticCounts   OBJECT-TYPE
   SYNTAX   INTEGER (0..255)
   ACCESS   read-write
   STATUS   mandatory
   DESCRIPTION
      "<Definition> Pedestrian Detector Erratic Counts 
       diagnostic Parameter in counts/minute (0-255 cpm). If 
       an active detector exhibits excessive actuations, it 
       is considered a fault by the diagnostics and the 
       detector is classified as Failed. A value of 0 for 
       this object shall disable this diagnostic for this 
       detector.
       <DescriptiveName> NTCIP-1202::ASC.pedestrianDetectorErraticCounts
       <DataConceptType> Data Element
       <Unit> count"
   REFERENCE
      "NEMA TS 2 Clause 3.9.3.1.4.3"
::= { pedestrianDetectorEntry 5 }

-- 2.2.7.6 PEDESTRIAN DETECTOR ALARMS

pedestrianDetectorAlarms  OBJECT-TYPE
   SYNTAX  INTEGER (0..255) 
   ACCESS   read-only
   STATUS   mandatory
   DESCRIPTION
      "<Definition> This object shall return indications of 
       detector alarms. Detector Alarms are indicated as 
       follows:
          Bit 7: Other Fault - The detector has failed due 
             to some other cause.
          Bit 6: Reserved.
          Bit 5: Reserved.
          Bit 4: Configuration Fault - Detector is assigned 
             but is not supported.
          Bit 3: Communications Fault - Communications to 
             the device (if present) have failed.
          Bit 2: Erratic Output Fault - This detector has 
             been flagged as non-operational due to erratic 
             outputs (excessive counts) by the CU detector 
             diagnostic.
          Bit 1: Max Presence Fault - This detector has been 
             flagged as non-operational due to a presence 
             indicator that exceeded the maximum expected 
             time by the CU detector diagnostic.
          Bit 0: No Activity Fault - This detector has been 
             flagged as non-operational due to lower than 
             expected activity by the CU detector diagnostic
       Once set a bit shall maintain its state as long as the 
       condition exists.  The bit shall clear when the condition
       no longer exists.
       <DescriptiveName> NTCIP-1202::ASC.pedestrianDetectorAlarms
       <DataConceptType> Data Element"
::= { pedestrianDetectorEntry  6 }

-- 2.3 UNIT PARAMETERS

unit OBJECT IDENTIFIER 
::= { asc 3 }

--This defines a node for supporting unit objects.

-- 2.3.1 STARTUP FLASH PARAMETER

unitStartUpFlash   OBJECT-TYPE
   SYNTAX   INTEGER (0..255)
   ACCESS   read-write
   STATUS   mandatory
   DESCRIPTION
      "<Definition> Unit Start up Flash time parameter in 
       seconds (0 to 255 sec). The period/state (Start-Up 
       Flash occurs when power is restored following a 
       device defined power interruption. During the 
       Start-Up Flash state, the Fault Monitor and Voltage 
       Monitor outputs shall be inactive (if present).
       <DescriptiveName> NTCIP-1202::ASC.unitStartUpFlash
       <DataConceptType> Data Element
       <Unit> second"
   REFERENCE
      "NEMA TS 2 Clause 3.9.1.1"
::= { unit 1 }


-- 2.3.2 AUTOMATIC PED CLEAR PARAMETER

unitAutoPedestrianClear   OBJECT-TYPE
   SYNTAX   INTEGER { disable(1),
                      enable (2) }
   ACCESS   read-write
   STATUS   mandatory
   DESCRIPTION
      "<Definition> Unit Automatic Ped Clear parameter 
       (1 = False/Disable 2=True/Enable). When enabled, 
       the CU shall time the Pedestrian Clearance interval 
       when Manual Control Enable is active and prevent the 
       Pedestrian Clearance interval from being terminated 
       by the Interval Advance input.
       <DescriptiveName> NTCIP-1202::ASC.unitAutoPedestrianClear
       <DataConceptType> Data Element"
   REFERENCE
      "NEMA TS 2 Clause 3.5.3.10"
::= { unit 2 }

-- 2.3.3 BACKUP TIME PARAMETER

unitBackupTime   OBJECT-TYPE
   SYNTAX   INTEGER (0..65535)
   ACCESS   read-write
   STATUS   mandatory
   DESCRIPTION
      "<Definition> The Backup Time in seconds (0-65535 sec). 
       When any of the defined system control parameters 
       is SET, the backup timer is reset. After reset it 
       times the unitBackupTime interval. If the unitBackupTime 
       interval expires without a SET operation to any of 
       the system control parameters, then the CU shall 
       revert to Backup Mode. A value of zero (0) for this 
       object shall disable this feature. The system control 
       parameters are: 
          phaseControlGroupPhaseOmit, 
          phaseControlGroupPedOmit, 
          phaseControlGroupHold, 
          phaseControlGroupForceOff, 
          phaseControlGroupVehCall, 
          phaseControlGroupPedCall, 
          systemPatternControl, 
          systemSyncControl, 
          preemptControlState, 
          ringControlGroupStopTime, 
          ringControlGroupForceOff, 
          ringControlGroupMax2, 
          ringControlGroupMaxInhibit, 
          ringControlGroupPedRecycle, 
          ringControlGroupRedRest, 
          ringControlGroupOmitRedClear, 
          unitControl, 
          specialFunctionOutputState, and 
          specialFunctionOutputControl.

       <DescriptiveName> NTCIP-1202::ASC.unitBackupTime
       <DataConceptType> Data Element
       <Unit> second"
::= { unit 3 }

-- 2.3.4 UNIT RED REVERT PARAMETER

unitRedRevert   OBJECT-TYPE
   SYNTAX   INTEGER (0..255)
   ACCESS   read-write
   STATUS   mandatory
   DESCRIPTION
      "<Definition> The red revert in tenth seconds ( 0.0 - 
       25.5 sec). This value shall provide the minimum 
       red revert time for all phases (i.e. if it is 
       greater than a phaseRedRevert object value, then 
       this value shall be used as the red revert time for 
       the affected phase). This object provides a minimum 
       Red indication following the Yellow Change interval 
       and prior to the next display of Green on the same 
       signal output driver group.
       <DescriptiveName> NTCIP-1202::ASC.unitRedRevert
       <DataConceptType> Data Element
       <Unit> tenth second"
::= { unit 4 }

-- 2.3.5 UNIT CONTROL STATUS

unitControlStatus   OBJECT-TYPE
   SYNTAX   INTEGER { other (1),
                      systemControl (2),
                      systemStandby (3),
                      backupMode(4),
                      manual (5),
                      timebase (6),
                      interconnect (7),
                      interconnectBackup (8)}
   ACCESS   read-only
   STATUS   mandatory
   DESCRIPTION
      "<Definition> The Control Mode for Pattern, Flash, or 
       Free at the device:
          other: control by a source other than those 
             listed here.
          systemControl: control by master or central 
             commands.
          systemStandby: control by local based on master or 
             central command to use local control.
          backupMode: Backup Mode (see Terms).
          manual: control by entry other than zero in 
             coordOperationalMode.
          timebase: control by the local Time Base.
          interconnect: control by the local Interconnect 
             inputs.
          interconnectBackup: control by local TBC due to 
             invalid Interconnect inputs or loss of sync.

       <DescriptiveName> NTCIP-1202::ASC.unitControlStatus
       <DataConceptType> Data Element"
::= { unit 5 }

-- 2.3.6 UNIT FLASH STATUS

unitFlashStatus   OBJECT-TYPE
   SYNTAX   INTEGER { other(1),
                      notFlash(2),
                      automatic(3),
                      localManual(4),
                      faultMonitor(5),
                      mmu(6),
                      startup(7),
                      preempt (8)}
   ACCESS   read-only
   STATUS   mandatory
   DESCRIPTION
      "<Definition> The Flash modes: 
         other: the CU is in flash for some other reason.
         notFlash: the CU is not in Flash 
         automatic: the CU is currently in an Automatic 
            Flash state.
         localManual: the Controller Unit Local Flash input 
            is active, MMU Flash input is not active, and 
            Flash is not commanded by the Master.
         faultMonitor: the CU is currently in a Fault 
            Monitor State.
         mmu: the Controller Unit MMU Flash input is active 
            and the CU is not in Start-Up Flash.
         startup: the CU is currently timing the Start-Up 
            Flash period.
         preempt: the CU is currently timing the preempt 
            Flash.
       <DescriptiveName> NTCIP-1202::ASC.unitFlashStatus
       <DataConceptType> Data Element"
::= { unit 6 }

-- 2.4 UNIT ALARM STATUS 2

unitAlarmStatus2   OBJECT-TYPE
   SYNTAX   INTEGER (0..255)
   ACCESS   read-only
   STATUS   mandatory
   DESCRIPTION
      "<Definition> Device Alarm Mask 2 ( 0 = False, 
       1 = True) as follows:
          Bit 7: Reserved.
          Bit 6: Reserved.
          Bit 5: Offset Transitioning - Whenever the CU is 
             performing an offset transition (correction in 
             process)
          Bit 4: Stop Time - When either CU Stop Time Input 
             becomes active.
          Bit 3: External Start - When the CU External Start 
             becomes active.
          Bit 2: Response Fault - When any NEMA TS2 Port 1 
             response frame fault occurs.
          Bit 1: Low Battery - When any battery voltage 
             falls below the required level.
          Bit 0: Power Restart - When power returns after a 
             power interruption.
       Once set, a bit shall maintain it’s state as long as 
       the condition exists. Bit 0 (Power Restart) status 
       shall be maintained until a READ of this object 
       occurs.
       <DescriptiveName> NTCIP-1202::ASC.unitAlarmStatus2
       <DataConceptType> Data Element"
::= { unit 7 }

-- 2.4.1 UNIT ALARM STATUS 1

unitAlarmStatus1   OBJECT-TYPE
   SYNTAX   INTEGER (0..255)
   ACCESS   read-only
   STATUS   mandatory
   DESCRIPTION
      "<Definition> Device Alarm Mask 1 ( 0 = False, 
       1 = True) as follows:
          Bit 7: CoordActive - When coordination is active 
             and not preempted or overridden.
          Bit 6: Local Free - When any of the CU inputs and/or
             programming cause it not to run coordination.
          Bit 5: Local Flash - When the Controller Unit 
             Local Flash input becomes active, MMU Flash 
             input is not active, and Flash is not commanded 
             by the system.
          Bit 4: MMU Flash - When the Controller Unit MMU 
             Flash input remains active for a period of time 
             exceeding the Start-Up Flash time.
          Bit 3: Cycle Fail - When a local Controller Unit 
             is operating in the non-coordinated mode, 
             whether the result of a Cycle Fault or Free 
             being the current normal mode, and cycling 
             diagnostics indicate that a serviceable call 
             exists that has not been serviced for two 
             cycles.
          Bit 2: Coord Fail - When a Coord Fault is in 
             effect and a Cycle Fault occurs again within 
             two cycles of the coordination retry.
          Bit 1: Coord Fault - When a Cycle Fault is in 
             effect and the serviceable call has been 
             serviced within two cycles after the Cycle 
             Fault.
          Bit 0: Cycle Fault - When the Controller Unit is 
             operating in the coordinated mode and cycling 
             diagnostics indicate that a serviceable call 
             exists that has not been serviced for two 
             cycles.
       Once set, a bit shall maintain it’s state as long as 
       the condition exists.
       <DescriptiveName> NTCIP-1202::ASC.unitAlarmStatus1
       <DataConceptType> Data Element"
::= { unit 8 }

-- 2.4.2 SHORT ALARM STATUS

shortAlarmStatus   OBJECT-TYPE
   SYNTAX   INTEGER (0..255)
   ACCESS   read-only
   STATUS   mandatory
   DESCRIPTION
      "<Definition> Short Alarm Mask ( 0 = False, 
       1 = True) as follows:
          Bit 7: Critical Alarm - When the Stop Time input 
             is active.
          Bit 6: Non-Critical Alarm - When an physical alarm 
             input is active.
          Bit 5: Detector Fault - When any detectorAlarm 
             fault occurs.
          Bit 4: Coordination Alarm - When the CU is not 
             running the called pattern without offset 
             correction within three cycles of the command. 
             An offset correction requiring less than three 
             cycles due to cycle overrun caused by servicing 
             a pedestrian call shall not cause a 
             Coordination Alarm.
          Bit 3: Local Override - When any of the CU inputs
             and/or programming cause it not to run coordination.
          Bit 2: Local Cycle Zero - When running coordinated 
             and the Coord Cycle Status (coordCycleStatus) 
             has passed through zero.
          Bit 1: T&F Flash - When either the Local Flash or 
             MMU Flash input becomes active.
          Bit 0: Preempt - When any of the CU Preempt 
             inputs become active.
       Once set, a bit shall maintain it’s state as long as 
       the condition exists. Bit 2 (Local Cycle Zero) status 
       shall be maintained until a READ of this object 
       occurs.
       <DescriptiveName> NTCIP-1202::ASC.shortAlarmStatus
       <DataConceptType> Data Element"
::= { unit 9 }

-- 2.4.3 UNIT CONTROL

unitControl   OBJECT-TYPE
   SYNTAX   INTEGER (0..255)
   ACCESS   read-write
   STATUS   mandatory
   DESCRIPTION
      "<Definition> This object is used to allow a remote 
       entity to activate unit functions in the device 
       ( 0 = False / Disabled, 1 = True / Enabled) as 
       follows:
          Bit 7: Dimming Enable - when set to 1, causes 
             channel dimming to operate as configured. For 
             dimming to occur, (this control OR a dimming 
             input) AND a 'timebaseAscAuxillaryFunction' 
             must be True.
             REFERENCE NEMA TS 2 Clause 3.9.2
          Bit 6: Interconnect - when set to 1, shall cause 
             the interconnect inputs to operate at a higher 
             priority than the timebase control (TBC On 
             Line).
             REFERENCE NEMA TS 2 Clause 3.6.2.3 and 3.8.3
          Bit 5: Walk Rest Modifier - when set to 1, causes 
             non-actuated phases to remain in the timed-out 
             Walk state (rest in Walk) in the absence of a 
             serviceable conflicting call.
             REFERENCE NEMA TS 2 Clause 3.5.5.5.13
          Bit 4: Call to Non-Actuated 2 - when set to 1, 
             causes any phase(s) appropriately programmed 
             in the phaseOptions object to operate in the 
             Non-Actuated Mode.
             REFERENCE NEMA TS 2 Clause 3.5.5.5.8
          Bit 3: Call to Non-Actuated 1 - when set to 1, 
             causes any phase(s) appropriately programmed 
             in the phaseOptions object to operate in the 
             Non-Actuated Mode.
             REFERENCE NEMA TS 2 Clause 3.5.5.5.8
          Bit 2: External Minimum Recall - when set to 1, 
             causes a recurring demand on all vehicle phases 
             for a minimum vehicle service.
             REFERENCE NEMA TS 2 Clause 3.5.5.5.9
          Bit 1: Reserved
          Bit 0: Reserved
       When a bit = 1, the device shall activate the Unit 
       control. When a bit = 0, the device shall not 
       activate the Unit control.

       A SET of a 'reserved' bit to a value other than 
       zero (0) shall return a badValue(3) error.

       The device shall reset this object to ZERO when in 
       BACKUP Mode. A write to this object shall reset the 
       BACKUP timer (see unitBackupTime).
       <DescriptiveName> NTCIP-1202::ASC.unitControl
       <DataConceptType> Data Element"
::= { unit 10 }

-- 2.4.4 MAXIMUM ALARM GROUPS

maxAlarmGroups   OBJECT-TYPE
   SYNTAX   INTEGER(1..255) 
   ACCESS   read-only
   STATUS   mandatory
   DESCRIPTION
      "<Definition> This object contains the maximum number 
       of alarm groups (8 alarm inputs per group) this 
       device supports.  This object indicates the maximum 
       rows which shall appear in the alarmGroupTable 
       object.
       <DescriptiveName> NTCIP-1202::ASC.maxAlarmGroups
       <DataConceptType> Data Element
       <Unit> alarm Group"
::= { unit 11 }
-- 2.4.5 ALARM GROUP TABLE

alarmGroupTable   OBJECT-TYPE
   SYNTAX   SEQUENCE OF AlarmGroupEntry 
   ACCESS   not-accessible
   STATUS   mandatory
   DESCRIPTION
      "<Definition> This table contains alarm input status 
       in groups of eight inputs. The number of rows in 
       this table is equal to the maxAlarmGroups object.
       <TableType> static
       <DescriptiveName> NTCIP-1202::ASC.alarmGroupTable
       <DataConceptType> Entity Type"
::= { unit 12 }

alarmGroupEntry   OBJECT-TYPE
   SYNTAX   AlarmGroupEntry
   ACCESS   not-accessible
   STATUS   mandatory
   DESCRIPTION
      "<Definition> Status for eight alarm inputs.
       <DescriptiveName> NTCIP-1202::ASC.alarmGroupEntry
       <DataConceptType> Entity Type"
   INDEX  { alarmGroupNumber }
::= { alarmGroupTable 1 }

AlarmGroupEntry::= SEQUENCE {
   alarmGroupNumber   INTEGER,
   alarmGroupState    INTEGER}

-- 2.4.5.1 ALARM GROUP NUMBER

alarmGroupNumber   OBJECT-TYPE
   SYNTAX   INTEGER (1..255)
   ACCESS   read-only
   STATUS   mandatory
   DESCRIPTION
      "<Definition> The alarm group number for objects in 
       this row.  This value shall not exceed the 
       maxAlarmGroups object value.
       <DescriptiveName> NTCIP-1202::ASC.alarmGroupNumber
       <DataConceptType> Data Element
       <Unit> group"
::= { alarmGroupEntry 1 }

-- 2.4.5.2 ALARM GROUP STATE

alarmGroupState   OBJECT-TYPE
   SYNTAX   INTEGER (0..255)
   ACCESS   read-only
   STATUS   mandatory
   DESCRIPTION
      "<Definition> Alarm input state bit field.  When a 
       bit = 1, the associated physical alarm input is 
       active.  When a bit = 0, the associated alarm input 
       is NOT active.
          Bit 7: Alarm Input # = ( alarmGroupNumber * 8)
          Bit 6: Alarm Input # = ( alarmGroupNumber * 8) -1
          Bit 5: Alarm Input # = ( alarmGroupNumber * 8) -2
          Bit 4: Alarm Input # = ( alarmGroupNumber * 8) -3
          Bit 3: Alarm Input # = ( alarmGroupNumber * 8) -4
          Bit 2: Alarm Input # = ( alarmGroupNumber * 8) -5
          Bit 1: Alarm Input # = ( alarmGroupNumber * 8) -6
          Bit 0: Alarm Input # = ( alarmGroupNumber * 8) -7
       <DescriptiveName> NTCIP-1202::ASC.alarmGroupState
       <DataConceptType> Data Element"
::= {alarmGroupEntry 2 }

-- 2.4.6 MAXIMUM SPECIAL FUNCTION OUTPUTS

maxSpecialFunctionOutputs   OBJECT-TYPE
   SYNTAX   INTEGER (1..255)
   ACCESS   read-only
   STATUS   mandatory
   DESCRIPTION
      "<Definition> The Maximum Number of Special Functions 
       this Actuated Controller Unit supports.
       <DescriptiveName> NTCIP-1202::ASC.maxSpecialFunctionOutputs
       <DataConceptType> Data Element
       <Unit> output"
::= { unit 13 }

-- 2.4.7 SPECIAL FUNCTION OUTPUT TABLE

specialFunctionOutputTable   OBJECT-TYPE
   SYNTAX   SEQUENCE OF SpecialFunctionOutputEntry
   ACCESS   not-accessible
   STATUS   mandatory
   DESCRIPTION
      "<Definition> A table containing Actuated Controller 
       Unit special function output objects. The number of 
       rows in this table is equal to the 
       maxSpecialFunctionOutputs object.
       <TableType> static
       <DescriptiveName> NTCIP-1202::ASC.specialFunctionOutputTable
       <DataConceptType> Entity Type"
::= { unit 14 }

specialFunctionOutputEntry   OBJECT-TYPE
   SYNTAX   SpecialFunctionOutputEntry
   ACCESS   not-accessible
   STATUS   mandatory
   DESCRIPTION
      "<Definition> Control for  Actuated Controller Unit 
       system special functions.
       <DescriptiveName> NTCIP-1202::ASC.specialFunctionOutputEntry
       <DataConceptType> Entity Type"
   INDEX   { specialFunctionOutputNumber }
::= { specialFunctionOutputTable 1 }

SpecialFunctionOutputEntry ::= SEQUENCE {
   specialFunctionOutputNumber   INTEGER,
--   specialFunctionOutputState    INTEGER,
   specialFunctionOutputControl  INTEGER,
   specialFunctionOutputStatus   INTEGER }

-- 2.4.7.1 SPECIAL FUNCTION OUTPUT NUMBER

specialFunctionOutputNumber   OBJECT-TYPE
   SYNTAX   INTEGER (1..255)
   ACCESS   read-only
   STATUS   mandatory
   DESCRIPTION
      "<Definition> The special function output number 
       associated with the specialFunctionOutputState 
       object in this row. This value shall not exceed the 
       maxSpecialFunctionOutputs object value.
       <DescriptiveName> NTCIP-1202::ASC.specialFunctionOutputNumber
       <DataConceptType> Data Element
       <Unit> output"
::= { specialFunctionOutputEntry 1 }

-- 2.4.7.2 SPECIAL FUNCTION OUTPUT STATE

-- { specialFunctionOutputEntry  2 } is deprecated ... see Annex D

-- 2.4.7.3 SPECIAL FUNCTION OUTPUT CONTROL

specialFunctionOutputControl   OBJECT-TYPE
   SYNTAX   INTEGER (0..1)
   ACCESS   read-write
   STATUS   mandatory
   DESCRIPTION
      "<Definition> The special function output (logical or 
       physical) in the device may be controlled by this 
       object. 
             0 = OFF & 1 = ON 
       The device shall reset this object to ZERO when in 
       BACKUP Mode. A write to this object shall reset the 
       BACKUP timer (see unitBackupTime).
       <DescriptiveName> NTCIP-1202::ASC.specialFunctionOutputControl
       <DataConceptType> Data Element"
::= { specialFunctionOutputEntry  3 }

-- 2.4.7.4 SPECIAL FUNCTION OUTPUT STATUS

specialFunctionOutputStatus   OBJECT-TYPE
   SYNTAX   INTEGER (0..1)
   ACCESS   read-only
   STATUS   mandatory
   DESCRIPTION
      "<Definition> The current status (ON-OFF) of the 
       special function output (logical or physical) in the 
       device.
             0 = OFF & 1 = ON 
       <DescriptiveName> NTCIP-1202::ASC.specialFunctionOutputStatus
       <DataConceptType> Data Element"
::= { specialFunctionOutputEntry  4 }
-- 2.5 COORDINATION PARAMETERS

coord   OBJECT IDENTIFIER
::= { asc 4 }

-- The coord node contains objects that support coordination 
-- configuration, status and control functions for the device.

-- 2.5.1 COORD OPERATIONAL MODE PARAMETER

coordOperationalMode   OBJECT-TYPE
   SYNTAX   INTEGER (0..255)
   ACCESS   read-write
   STATUS   mandatory
   DESCRIPTION
      "<Definition> This object defines the operational 
       mode for coordination. The possible modes are:
         Value   Description
           0     Automatic - this mode provides for coord 
                 operation, free, and flash to be determined 
                 automatically by the possible sources (i.e. 
                 Interconnect, Time Base, or System Commands).
          1-253  Manual Pattern - these modes provides for 
                 Coord operation running this pattern.  This 
                 selection of pattern overrides all other 
                 pattern commands.
          254    Manual Free - this mode provides for Free 
                 operation without coordination or Automatic 
                 Flash from any source.
          255    Manual Flash - this mode provides for 
                 Automatic Flash without coordination or 
                 Free from any source.
       <DescriptiveName> NTCIP-1202::ASC.coordOperationalMode
       <DataConceptType> Data Element"
   REFERENCE
      "NEMA TS 2 Clause 3.6.2.4"
::= { coord 1 }

-- 2.5.2 COORD CORRECTION MODE PARAMETER

coordCorrectionMode   OBJECT-TYPE
   SYNTAX   INTEGER { other (1),
                      dwell (2),
                      shortway (3),
                      addOnly (4) }
   ACCESS   read-write
   STATUS   mandatory
   DESCRIPTION
      "<Definition> This object defines the Coord Correction 
       Mode. The possible modes are:
         other: the coordinator establishes a new offset by 
            a mechanism not defined in this standard.
         dwell: when changing offset, the coordinator shall 
            establish a new offset by dwelling in the coord 
            phase(s) until the desired offset is reached.

         shortway (Smooth): when changing offset, the 
            coordinator shall establish a new offset by 
            adding or subtracting to/from the timings in a 
            manner that limits the cycle change. This 
            operation is performed in a device specific 
            manner.
         addOnly: when changing offset, the coordinator 
            shall establish a new offset by adding to the 
            timings in a manner that limits the cycle 
            change. This operation is performed in a device 
            specific manner.
       <DescriptiveName> NTCIP-1202::ASC.coordCorrectionMode
       <DataConceptType> Data Element"
::= { coord 2 }

-- 2.5.3 COORD MAXIMUM MODE PARAMETER

coordMaximumMode   OBJECT-TYPE
   SYNTAX   INTEGER { other (1),
                      maximum1 (2),
                      maximum2 (3),
                      maxInhibit (4) }
   ACCESS   read-write
   STATUS   mandatory
   DESCRIPTION
      "This object defines the Coord Maximum Mode. The possible 
       modes are:
          other: the maximum mode is determined by some 
             other mechanism not defined in this standard.
          maximum1: the internal Maximum 1 Timing shall be 
             effective while coordination is running a 
             pattern. 
          maximum2: the internal Maximum 2 Timing shall be 
             effective while coordination is running a 
             pattern. 
          maxInhibit: the internal Maximum Timing shall be 
             inhibited while coordination is running a 
             pattern.
       <DescriptiveName> NTCIP-1202::ASC.coordMaximumMode
       <DataConceptType> Data Element"
::= { coord 3 }

-- 2.5.4 COORD FORCE MODE PARAMETER

coordForceMode   OBJECT-TYPE
   SYNTAX   INTEGER { other(1),
                      floating (2),
                      fixed (3) }
   ACCESS   read-write
   STATUS   mandatory
   DESCRIPTION
      "<Definition> This object defines the Pattern Force 
       Mode. The possible modes are:
          other: the CU implements a mechanism not defined 
             in this standard.
          floating: each non-coord phase will be forced to 
             limit its time to the split time value. This allows 
             unused split time to revert to the coord phase.
          fixed: each non-coord phase will be forced at a fixed 
             position in the cycle. This allows unused 
             split time to revert to the following phase.
       <DescriptiveName> NTCIP-1202::ASC.coordForceMode
       <DataConceptType> Data Element"
::= { coord 4 }

-- 2.5.5 MAXIMUM PATTERNS PARAMETER

maxPatterns   OBJECT-TYPE
   SYNTAX   INTEGER (1..253)
   ACCESS   read-only
   STATUS   mandatory
   DESCRIPTION
      "<Definition> The maximum number of Patterns this 
       Actuated Controller Unit supports. This object 
       indicates how many rows are in the patternTable 
       object (254 and 255 are defined as non-pattern 
       status for Free and Flash).
       <DescriptiveName> NTCIP-1202::ASC.maxPatterns
       <DataConceptType> Data Element
       <Unit> pattern"
::= { coord 5 }

-- 2.5.6 PATTERN TABLE TYPE

patternTableType   OBJECT-TYPE
   SYNTAX   INTEGER { other (1),
                     patterns (2),
                     offset3 (3),
                     offset5 (4) }
   ACCESS   read-only
   STATUS   mandatory
   DESCRIPTION
      "<Definition> This object provides information about 
       any special organizational structure required for 
       the pattern table. The defined structures are as 
       follows:
          other: The pattern table setup is not described 
             in this standard, refer to device manual.
          patterns: Each row of the pattern table 
             represents a unique pattern and has no 
             dependencies on other rows.
          offset3: The pattern table is organized into 
             plans which have three offsets.  Each plan 
             uses three consecutive rows.  Only 
             patternOffsetTime and patternSequenceNumber
             values may vary between each of the three rows. 
             Plan 1 is contained in rows 1, 2 and 3, Plan 2 
             is contained in rows 4, 5 and 6, Plan 3 is in 
             rows 7, 8 and 9, etc.

          offset5:  The pattern table is organized into 
             plans which have five offsets.  Each plan 
             occupies five consecutive rows.  Only 
             patternOffsetTime and patternSequenceNumber 
             values may vary between each of the rows.  
             Plan 1 is contained in rows 1, 2, 3, 4 and 
             5, Plan 2 is contained in rows 6, 7, 8, 9 and 
             10, Plan 3 is contained in rows 11, 12, 13, 14 
             and 15, etc.
       <DescriptiveName> NTCIP-1202::ASC.patternTableType
       <DataConceptType> Data Element"
   REFERENCE
      "NEMA TS 2 Clause 3.6.2.1 and 3.6.2.2"
::= { coord 6 }

-- 2.5.7 PATTERN TABLE

patternTable   OBJECT-TYPE
   SYNTAX   SEQUENCE OF PatternEntry
   ACCESS   not-accessible
   STATUS   mandatory
   DESCRIPTION
      "<Definition> A table containing Actuated Controller 
       Unit coordination Pattern parameters. The number of 
       rows in this table is equal to the maxPatterns object.
       <TableType> static
       <DescriptiveName> NTCIP-1202::ASC.patternTable
       <DataConceptType> Entity Type"
::= { coord 7 }

patternEntry   OBJECT-TYPE
   SYNTAX   PatternEntry
   ACCESS   not-accessible
   STATUS   mandatory
   DESCRIPTION
      "<Definition> Parameters for a specific Actuated 
       Controller Unit pattern.
       <DescriptiveName> NTCIP-1202::ASC.patternEntry
       <DataConceptType> Entity Type"
   INDEX   { patternNumber }
::= { patternTable 1 }

PatternEntry ::= SEQUENCE {
   patternNumber           INTEGER,
   patternCycleTime        INTEGER,
   patternOffsetTime       INTEGER,
   patternSplitNumber      INTEGER,
   patternSequenceNumber   INTEGER }


-- 2.5.7.1 PATTERN NUMBER ENTRY

patternNumber   OBJECT-TYPE
   SYNTAX   INTEGER (1..253)
   ACCESS   read-only
   STATUS   mandatory
   DESCRIPTION
      "<Definition> The pattern number for objects in this 
       row. This value shall not exceed the maxPatterns 
       object value.
       <DescriptiveName> NTCIP-1202::ASC.patternNumber
       <DataConceptType> Data Element
       <Unit> pattern"
::= { patternEntry 1 }

-- 2.5.7.2 PATTERN CYCLE TIME

patternCycleTime   OBJECT-TYPE
   SYNTAX   INTEGER (0..255)
   ACCESS   read-write
   STATUS   mandatory
   DESCRIPTION
      "<Definition> The patternCycleTime object specifies 
       the length of the pattern cycle in seconds (NEMA 
       TS 2 range: 30-255).  A pattern cycle time less than 
       adequate to service the minimum requirements of all 
       phases shall result in Free mode. While this condition
       exists, the Local Free bit of unitAlarmStatus1 and the
       Local Override bit of shortAlarmStatus shall be set to 
       one (1). 

       The minimum requirements of a phase with a not-actuated
       ped include Minimum Green, Walk, Pedestrian Clear, Yellow 
       Clearance, and Red Clearance; the minimum requirements of 
       a phase with an actuated pedestrian include Minimum Green, 
       Yellow Clearance, and Red Clearance. If the pattern cycle 
       time is zero and the associated split table (if any) 
       contains values greater than zero, then the CU shall 
       utilize the split time values as maximum values for each 
       phase.
       <DescriptiveName> NTCIP-1202::ASC.patternCycleTime
       <DataConceptType> Data Element
       <Unit> second"
   REFERENCE
      "NEMA TS 2 Clause 3.6.2.1.1"
::= { patternEntry 2 }


-- 2.5.7.3 PATTERN OFFSET TIME PARAMETER

patternOffsetTime   OBJECT-TYPE
   SYNTAX   INTEGER (0..255)
   ACCESS   read-write
   STATUS   mandatory
   DESCRIPTION
      "<Definition> The patternOffsetTime defines by how 
       many seconds (NEMA TS 2 range: 0-254) the local time 
       zero shall lag the system time zero (synchronization 
       pulse) for this pattern. An offset value equal to 
       or greater than the patternCycleTime shall result in Free 
       being the operational mode.  While this condition 
       exists, the Local Free bit of unitAlarmStatus1 and 
       the LocalOverride bit of shortAlarmStatus shall be 
       set to one (1).
       <DescriptiveName> NTCIP-1202::ASC.patternOffsetTime
       <DataConceptType> Data Element
       <Unit> second"
   REFERENCE
      "NEMA TS 2 Clause 3.6.2.2"
::= { patternEntry 3 }

-- 2.5.7.4 PATTERN SPLIT NUMBER PARAMETER

patternSplitNumber   OBJECT-TYPE
   SYNTAX   INTEGER (1..255)
   ACCESS   read-only
   STATUS   mandatory
   DESCRIPTION
      "<Definition> This object is used to locate 
       information in the splitTable to use for this 
       pattern. This value shall not exceed the maxSplits 
       object value.
       <DescriptiveName> NTCIP-1202::ASC.patternSplitNumber
       <DataConceptType> Data Element
       <Unit> split"
::= { patternEntry 4 }

-- 2.5.7.5 PATTERN SEQUENCE NUMBER PARAMETER

patternSequenceNumber   OBJECT-TYPE
   SYNTAX   INTEGER (1..255)
   ACCESS   read-write
   STATUS   mandatory
   DESCRIPTION
      "<Definition> This object is used to locate 
       information in the sequenceTable to use with this 
       pattern. This value shall not exceed the 
       maxSequences object value.
       <DescriptiveName> NTCIP-1202::ASC.patternSequenceNumber
       <DataConceptType> Data Element
       <Unit> sequence"
::= { patternEntry 5 }

-- 2.5.8 MAXIMUM SPLITS

maxSplits   OBJECT-TYPE
   SYNTAX   INTEGER (1..255)
   ACCESS   read-only
   STATUS   mandatory
   DESCRIPTION
      "<Definition> The maximum number of Split Plans this 
       Actuated Controller Unit supports. This object 
       indicates how many Split plans are in the splitTable 
       object.
       <DescriptiveName> NTCIP-1202::ASC.maxSplits
       <DataConceptType> Data Element
       <Unit> split"
::= { coord 8 }

-- 2.5.9 SPLIT TABLE

splitTable   OBJECT-TYPE
   SYNTAX   SEQUENCE OF SplitEntry
   ACCESS   not-accessible
   STATUS   mandatory
   DESCRIPTION
      "<Definition> A table containing Actuated Controller 
       Unit coordination split parameters. The number of 
       rows in this table is equal to maxSplits.
       <TableType> static
       <DescriptiveName> NTCIP-1202::ASC.splitTable
       <DataConceptType> Entity Type"
::= { coord 9 }

splitEntry   OBJECT-TYPE
   SYNTAX   SplitEntry
   ACCESS   not-accessible
   STATUS   mandatory
   DESCRIPTION
      "<Definition> Split type Parameters for a specific 
       Actuated Controller Unit phase.
       <DescriptiveName> NTCIP-1202::ASC.splitEntry
       <DataConceptType> Entity Type"
   INDEX   { splitNumber, splitPhase }
::= { splitTable 1 }

SplitEntry ::= SEQUENCE {
   splitNumber       INTEGER,
   splitPhase        INTEGER,
   splitTime         INTEGER,
   splitMode         INTEGER,
   splitCoordPhase   INTEGER }

-- 2.5.9.1 SPLIT NUMBER

splitNumber   OBJECT-TYPE
   SYNTAX   INTEGER (1..255)
   ACCESS   read-only
   STATUS   mandatory
   DESCRIPTION
      "<Definition> The object defines which rows of the 
       split table comprise a split group. All rows that 
       have the same splitNumber are in the same split 
       group. The value of this object shall not exceed the 
       maxSplits object value.
       <DescriptiveName> NTCIP-1202::ASC.splitNumber
       <DataConceptType> Data Element
       <Unit> split"
::= { splitEntry 1 }

-- 2.5.9.2 SPLIT PHASE NUMBER

splitPhase   OBJECT-TYPE
   SYNTAX   INTEGER (1..255)
   ACCESS   read-only
   STATUS   mandatory
   DESCRIPTION
      "<Definition> The phase number for objects in this 
       row. The value of this object shall not exceed the 
       maxPhases object value.
       <DescriptiveName> NTCIP-1202::ASC.splitPhase
       <DataConceptType> Data Element
       <Unit> phase"
::= { splitEntry 2 }

-- 2.5.9.3 SPLIT TIME PARAMETER

splitTime   OBJECT-TYPE
   SYNTAX   INTEGER (0..255)
   ACCESS   read-write
   STATUS   mandatory
   DESCRIPTION
      "<Definition> The time in seconds the splitPhase is 
       allowed to receive (i.e. before a Force Off is 
       applied) when constant demands exist on all phases. 
       In floating coordForceMode, this is always the 
       maximum time a non-coordinated phase is allowed to 
       receive.  In fixed coordForceMode, the actual allowed 
       time may be longer if a previous phase gapped out. 

       The splitTime includes all phase clearance times for 
       the associated phase. The split time shall be longer 
       than the sum of the phase minimum service 
       requirements for the phase. When the time is NOT 
       adequate to service the minimum service requirements 
       of the phase, Free Mode shall be the result. The 
       minimum requirements of a phase with a not-actuated 
       ped include Minimum Green, Walk, Pedestrian Clear, 
       Yellow Clearance, and Red Clearance; the minimum 
       requirements of a phase with an actuated pedestrian 
       include Minimum Green, Yellow Clearance, and Red 
       Clearance.

       If the cycleTime entry of the associated 
       patternTable entry is zero (i.e. the device is in 
       Free Mode), then the value of this object shall be 
       applied, if non-zero, as a maximum time for the 
       associated phase.

       If the critical path through the phase diagram is 
       less than the cycleTime entry of the associated 
       patternTable entry, all extra time is alloted to the 
       coordination phase in each ring.

       If the critical path through the phase diagram is 
       greater than the cycleTime entry of the associated 
       patternTable entry (and the cycleTime is not zero) 
       the device shall operate in the Free Mode.

       While the Free Mode condition exists, the Local 
       Override bit of shortAlarm shall be set to one (1).
       <DescriptiveName> NTCIP-1202::ASC.splitTime
       <DataConceptType> Data Element
       <Unit> second"
   REFERENCE
      "NEMA TS 2 Clause 3.6.2.1.2"
::= { splitEntry 3 }

-- 2.5.9.4 SPLIT MODE PARAMETER

splitMode   OBJECT-TYPE
   SYNTAX   INTEGER { other(1),
                      none (2),
                      minimumVehicleRecall (3),
                      maximumVehicleRecall (4),
                      pedestrianRecall (5),
                      maximumVehicleAndPedestrianRecall (6),
                      phaseOmitted (7) }
   ACCESS   read-write
   STATUS   mandatory
   DESCRIPTION
      "<Definition> This object defines operational 
       characteristics of the phase. The following options 
       are available:
         other: the operation is not specified in this 
            standard
         none: no split mode control.
         minimumVehicleRecall: this phase operates with a 
            minimum vehicle recall.
         maximumVehicleRecall: this phase operates with a 
            maximum vehicle recall.
         pedestrianRecall: this phase operates with a 
            pedestrian recall.
         maximumVehicleAndPedestrianRecall: this phase 
            operates with a maximum vehicle & pedestrian 
            recall.
         phaseOmitted: this phase is omitted.

       <DescriptiveName> NTCIP-1202::ASC.splitMode
       <DataConceptType> Data Element"
::= { splitEntry 4 }

-- 2.5.9.5 SPLIT COORDINATED PHASE

splitCoordPhase  OBJECT-TYPE
   SYNTAX   INTEGER (0..1)
   ACCESS   read-write
   STATUS   mandatory
   DESCRIPTION
      "<Definition> To select the associated phase as a 
       coordinated phase this object shall be set to TRUE 
       (non zero).
       <DescriptiveName> NTCIP-1202::ASC.splitCoordPhase
       <DataConceptType> Data Element"
::= { splitEntry 5 }

-- 2.5.10 COORDINATION PATTERN STATUS 

coordPatternStatus   OBJECT-TYPE
   SYNTAX   INTEGER (0..255)
   ACCESS   read-only
   STATUS   mandatory
   DESCRIPTION
      "<Definition> This object defines the running 
       coordination pattern/mode in the device. The 
       possible values are:
         Value Description
           0   Not used
         1-253 Pattern - indicates the currently running 
               pattern
          254  Free - indicates Free operation without 
               coordination.
          255  Flash - indicates Automatic Flash without 
               coordination.
       <DescriptiveName> NTCIP-1202::ASC.coordPatternStatus
       <DataConceptType> Data Element"
::= { coord 10 }

-- 2.5.11 LOCAL FREE STATUS

localFreeStatus   OBJECT-TYPE
SYNTAX   INTEGER { other(1),
                   notFree(2),
                   commandFree(3),
                   transitionFree(4),
                   inputFree(5),
                   coordFree(6),
                   badPlan(7),
                   badCycleTime(8),
                   splitOverrun (9),
                   invalidOffset (10),
                   failed(11) }
   ACCESS   read-only
   STATUS   mandatory
   DESCRIPTION
      "<Definition> The Free modes: 
         other: Some other condition has caused the device 
            to run in free mode.
         notFree: The unit is not running in free mode.
         commandFree: the current pattern command is the 
            Free mode pattern.
         transitionFree: the CU has a pattern command but 
            is cycling to a point to begin coordination.
         inputFree: one of the CU inputs cause it to not 
            respond to coordination.
         coordFree: the CU programming for the called 
            pattern is to run Free.
         badPlan: Free - the called pattern is invalid.
         badCycleTime: the pattern cycle time is less than
            adequate to service the minimum requirements of
            all phases.
         splitOverrun: Free - the sum of the critical path 
            splitTime’s exceed the programmed 
            patternCycleTime value.
         invalidOffset: Free - reserved / not used
         failed: cycling diagnostics have called for Free.

       An ASC may provide diagnostics beyond those stated 
       herein. Therefore, for a set of given bad data, the 
       free status between devices may be inconsistent.
       <DescriptiveName> NTCIP-1202::ASC.localFreeStatus
       <DataConceptType> Data Element"
::= { coord 11 }

-- 2.5.12 COORDINATION CYCLE STATUS

coordCycleStatus   OBJECT-TYPE
   SYNTAX   INTEGER (0..510)
   ACCESS   read-only
   STATUS   mandatory
   DESCRIPTION
      "<Definition> The Coord Cycle Status represents the 
       current position in the local coord cycle of the 
       running pattern (0 to 510 sec). This value normally 
       counts down from patternCycleTime to Zero. This 
       value may exceed the patternCycleTime during a coord 
       cycle with offset correction (patternCycleTime + 
       correction).
       <DescriptiveName> NTCIP-1202::ASC.coordCycleStatus
       <DataConceptType> Data Element
       <Unit> second"
::= { coord 12 }

-- 2.5.13 COORDINATION SYNC STATUS

coordSyncStatus   OBJECT-TYPE
   SYNTAX   INTEGER (0..510)
   ACCESS   read-only
   STATUS   mandatory
   DESCRIPTION
      "<Definition> The Coord Sync Status represents the 
       time since the system reference point for the 
       running pattern (0 to 510 sec). This value normally 
       counts up from Zero to the next system reference 
       point (patternCycleTime). This value may exceed the 
       patternCycleTime during a coord cycle in which the 
       system reference point has changed.
       <DescriptiveName> NTCIP-1202::ASC.coordSyncStatus
       <DataConceptType> Data Element
       <Unit> second"
::= { coord 13 }

-- 2.5.14 SYSTEM PATTERN CONTROL

systemPatternControl   OBJECT-TYPE
   SYNTAX   INTEGER (0..255)
   ACCESS   read-write
   STATUS   mandatory
   DESCRIPTION
      "<Definition> This object is used to establish the 
       Called System Pattern/Mode for the device. The 
       possible values are:
         Value   Description
           0     Standby - the system relinquishes control 
                 of the device.
         1-253   Pattern - these values indicate the system 
                 commanded pattern
          254    Free - this value indicates a call for Free 
          255    Flash - this value indicates a call for 
                 Automatic Flash
       If an unsupported / invalid pattern is called, Free 
       shall be the operational mode.
       The device shall reset this object to ZERO when in 
       BACKUP Mode. A write to this object shall reset the 
       Backup timer to ZERO (see unitBackupTime).
       <DescriptiveName> NTCIP-1202::ASC.systemPatternControl
       <DataConceptType> Data Element"
::= { coord 14 }


-- 2.5.15 SYSTEM SYNC CONTROL

systemSyncControl   OBJECT-TYPE
   SYNTAX   INTEGER (0..255)
   ACCESS   read-write
   STATUS   mandatory
   DESCRIPTION
      "<Definition> This object is used to establish the 
       system reference point for the Called System Pattern 
       by providing the current position in the system 
       pattern cycle (0-254 sec). The device shall 
       recognize a write to this object as a command to 
       establish the time until the next system reference 
       point. Thereafter, the system reference point shall 
       be assumed to occur at a frequency equal to the 
       patternCycleTime.

       When the value in the object is 255, the system 
       reference point shall be referenced to the local 
       Time Base in accordance with its programming.

       This CU must maintain an accuracy of 0.1 seconds 
       based on the receipt of the SET packet.
       The device shall reset this object to ZERO when in 
       BACKUP Mode. A write to this object shall reset the 
       Backup timer to ZERO (see unitBackupTime).
       <DescriptiveName> NTCIP-1202::ASC.systemSyncControl
       <DataConceptType> Data Element
       <Unit> second"
::= { coord  15 }

-- 2.6 TIME BASE PARAMETERS

timebaseAsc OBJECT IDENTIFIER
::= { asc 5 }

-- This object is an identifier used to group all objects for 
-- support of timebase functions.  If a device implements timebase 
-- functions then these objects shall be supported.

-- 2.6.1 TIME BASE PATTERN SYNC PARAMETER

timebaseAscPatternSync   OBJECT-TYPE
   SYNTAX   INTEGER (0..65535)
   ACCESS   read-write
   STATUS   mandatory
   DESCRIPTION
      "<Definition> Pattern Sync Reference in minutes past 
       midnight.  When the value is 65535, the controller 
       unit shall use the Action time as the Sync Reference 
       for that pattern. Action time is the hour and minute
       associated with the active dayPlanEventNumber (as
       defined in NTCIP 1201).

       <DescriptiveName> NTCIP-1202::ASC.timebaseAscPatternSync
       <DataConceptType> Data Element
       <Unit> minute"
   REFERENCE
      "NEMA TS 2 Clause 3.8.2"
::= { timebaseAsc 1 }

-- 2.6.2 MAXIMUM TIME BASE ACTIONS 

maxTimebaseAscActions   OBJECT-TYPE
   SYNTAX   INTEGER (1..255)
   ACCESS   read-only
   STATUS   mandatory
   DESCRIPTION
      "<Definition> The Maximum Number of Actions this 
       device supports. This object indicates the maximum 
       rows which shall appear in the 
       timebaseAscActionTable object.
       <DescriptiveName> NTCIP-1202::ASC.maxTimebaseAscActions
       <DataConceptType> Data Element
       <Unit> action"
::= { timebaseAsc 2 }

-- 2.6.3 TIME BASE ASC ACTION TABLE

timebaseAscActionTable   OBJECT-TYPE
   SYNTAX   SEQUENCE OF TimebaseAscActionEntry
   ACCESS   not-accessible
   STATUS   mandatory
   DESCRIPTION
      "<Definition> A table containing Actuated Controller 
       Unit Time Base action parameters. The number of rows 
       in this table is equal to the maxTimebaseAscActions 
       object.
       <TableType> static
       <DescriptiveName> NTCIP-1202::ASC.timebaseAscActionTable
       <DataConceptType> Entity Type"
::= { timebaseAsc 3 }

timebaseAscActionEntry   OBJECT-TYPE
   SYNTAX   TimebaseAscActionEntry
   ACCESS   not-accessible
   STATUS   mandatory
   DESCRIPTION
      "<Definition> Action Parameters for a Actuated 
       Controller Unit Time Base Program.
       <DescriptiveName> NTCIP-1202::ASC.timebaseAscActionEntry
       <DataConceptType> Entity Type"
   INDEX   { timebaseAscActionNumber }
::= { timebaseAscActionTable 1 }

TimebaseAscActionEntry ::= SEQUENCE { 
   timebaseAscActionNumber        INTEGER,
   timebaseAscPattern             INTEGER,
   timebaseAscAuxillaryFunction   INTEGER,
   timebaseAscSpecialFunction     INTEGER }

-- 2.6.3.1 TIME BASE ACTION NUMBER

timebaseAscActionNumber   OBJECT-TYPE
   SYNTAX   INTEGER (1..255)
   ACCESS   read-only
   STATUS   mandatory
   DESCRIPTION
      "<Definition> The time base Action number for objects 
       in this row. This value shall not exceed the 
       maxTimebaseAscActions object value.
         This object may be defined as a dayPlanActionOID (as
       defined in NTCIP 1201).
       <DescriptiveName> NTCIP-1202::ASC.timebaseAscActionNumber
       <DataConceptType> Data Element
       <Unit> action"
::= { timebaseAscActionEntry 1 }

-- 2.6.3.2 TIME BASE ACTION PATTERN PARAMETER

timebaseAscPattern   OBJECT-TYPE
   SYNTAX   INTEGER (0..255)
   ACCESS   read-write
   STATUS   mandatory
   DESCRIPTION
      "<Definition> The Pattern that shall be active when 
       this Action is active. The value shall not exceed 
       the value of maxPatterns, except for flash or free.  A pattern 
       of zero indicates that no pattern is being selected.
       A pattern = 0 relinquishes control to entity of a 
       lower priority than timebase and allows that entity 
       to control (i.e., interconnect if available).
       <DescriptiveName> NTCIP-1202::ASC.timebaseAscPattern
       <DataConceptType> Data Element
       <Unit> pattern"
::= { timebaseAscActionEntry 2 }

-- 2.6.3.3 TIME BASE ACTION AUXILIARY FUNCTION PARAMETER

timebaseAscAuxillaryFunction   OBJECT-TYPE
   SYNTAX   INTEGER (0..255)
   ACCESS   read-write
   STATUS   mandatory
   DESCRIPTION
      "<Definition> The Auxiliary functions that shall be 
       active when this Action is active.
          Bit 7: Reserved
          Bit 6: Reserved
          Bit 5: Reserved
          Bit 4: Reserved
          Bit 3: Dimming enabled if set (non-zero), 
             disabled if clear (zero). For dimming to 
             occur, this control AND ('unitControl' OR a 
             dimming input) must be True.
          Bit 2: Auxiliary Function 3 enabled if set 
             (non-zero), disabled if clear (zero).
          Bit 1: Auxiliary Function 2 enabled if set 
             (non-zero), disabled if clear (zero).
          Bit 0: Auxiliary Function 1 enabled if set 
             (non-zero), disabled if clear (zero).
       A SET of a 'reserved' bit to a value other than 
       zero (0) shall return a badValue(3) error.
       <DescriptiveName> NTCIP-1202::ASC.timebaseAscAuxillaryFunction
       <DataConceptType> Data Element"
::= { timebaseAscActionEntry 3 }

-- 2.6.3.4 TIME BASE ACTION SPECIAL FUNCTION PARAMETER

timebaseAscSpecialFunction   OBJECT-TYPE
   SYNTAX   INTEGER (0..255)
   ACCESS   read-write
   STATUS   mandatory
   DESCRIPTION
      "<Definition> The Special Functions that shall be 
       active when this Action is active.
          Bit 7: Special Function 8
          Bit 6: Special Function 7
          Bit 5: Special Function 6
          Bit 4: Special Function 5
          Bit 3: Special Function 4
          Bit 2: Special Function 3
          Bit 1: Special Function 2
          Bit 0: Special Function 1
       Bit = 0 - False/Disabled, Bit = 1 - True/Enabled
       <DescriptiveName> NTCIP-1202::ASC.timebaseAscSpecialFunction
       <DataConceptType> Data Element"
::= { timebaseAscActionEntry 4 }

-- 2.6.4 TIME BASE ASC ACTION STATUS

timebaseAscActionStatus   OBJECT-TYPE
   SYNTAX   INTEGER(0..255)
   ACCESS   read-only
   STATUS   mandatory
   DESCRIPTION
      "<Definition> This object indicates the current time 
       base Action Table row that will be used when the CU 
       is in Time Base operation. A value of zero indicates 
       that no time base Action is selected.
       <DescriptiveName> NTCIP-1202::ASC.timebaseAscActionStatus
       <DataConceptType> Data Element"
::= { timebaseAsc 4 }

-- 2.7 PREEMPT PARAMETERS

preempt OBJECT IDENTIFIER
::= { asc 6 }

-- The preempt node contains objects that support preempt input 
-- functions for the device.

-- 2.7.1 MAXIMUM PREEMPTS

maxPreempts   OBJECT-TYPE
   SYNTAX   INTEGER (1..255)
   ACCESS   read-only
   STATUS   mandatory
   DESCRIPTION
      "<Definition> The Maximum Number of Preempts this 
       Actuated Controller Unit supports. This object 
       indicates the maximum rows which shall appear in the 
       preemptTable object.
       <DescriptiveName> NTCIP-1202::ASC.maxPreempts
       <DataConceptType> Data Element
       <Unit> preempt"
   REFERENCE
      "NEMA TS 2 Clause 3.7"
::= { preempt 1 }

-- 2.7.2 PREEMPT TABLE

preemptTable   OBJECT-TYPE
   SYNTAX   SEQUENCE OF PreemptEntry
   ACCESS   not-accessible
   STATUS   mandatory
   DESCRIPTION
      "<Definition> A table containing Actuated Controller 
       Unit preemption parameters. The number of rows in 
       this table is equal to the maxPreempts object.
       <TableType> static
       <DescriptiveName> NTCIP-1202::ASC.preemptTable
       <DataConceptType> Entity Type"
::={ preempt 2 }

preemptEntry   OBJECT-TYPE
   SYNTAX   PreemptEntry
   ACCESS   not-accessible
   STATUS   mandatory
   DESCRIPTION
      "<Definition> Parameters for a specific Actuated 
       Controller Unit preemptor.
       <DescriptiveName> NTCIP-1202::ASC.preemptEntry
       <DataConceptType> Entity Type"
   INDEX    { preemptNumber }
::={ preemptTable 1}

PreemptEntry ::= SEQUENCE {
   preemptNumber            INTEGER,
   preemptControl           INTEGER,
   preemptLink              INTEGER,
   preemptDelay             INTEGER,
   preemptMinimumDuration   INTEGER,
   preemptMinimumGreen      INTEGER,
   preemptMinimumWalk       INTEGER,
   preemptEnterPedClear     INTEGER,
   preemptTrackGreen        INTEGER,
   preemptDwellGreen        INTEGER,
   preemptMaximumPresence   INTEGER,
   preemptTrackPhase        OCTET STRING,
   preemptDwellPhase        OCTET STRING,
   preemptDwellPed          OCTET STRING,
   preemptExitPhase         OCTET STRING,
   preemptState             INTEGER,
   preemptTrackOverlap      OCTET STRING,
   preemptDwellOverlap      OCTET STRING,
   preemptCyclingPhase      OCTET STRING,
   preemptCyclingPed        OCTET STRING,
   preemptCyclingOverlap    OCTET STRING,
   preemptEnterYellowChange INTEGER,
   preemptEnterRedClear     INTEGER,
   preemptTrackYellowChange INTEGER,
   preemptTrackRedClear     INTEGER }

-- 2.7.2.1 PREEMPT NUMBER

preemptNumber   OBJECT-TYPE
   SYNTAX   INTEGER (1..255)
   ACCESS   read-only
   STATUS   mandatory
   DESCRIPTION
      "<Definition> The preempt number for objects in this 
       row. The value shall not exceed the maxPreempts 
       object value.
         When all preemptControl objects have a value where 
       bit 2 = 0, each preemptNumber routine shall be a higher
       priority and override all preemptNumber routines that 
       have a larger preemptNumber.
         When a preemptControl object has a value where 
       bit 2 = 1, the next higher preemptNumber becomes of 
       equal priority with the preemptNumber but may still be
       a higher priority than larger preemptNumbers depending
       on bit 2 of the relavent preemptControl objects.
       <DescriptiveName> NTCIP-1202::ASC.preemptNumber
       <DataConceptType> Data Element
       <Unit> preempt"
::= { preemptEntry 1 }

-- 2.7.2.2 PREEMPT CONTROL PARAMETER

preemptControl   OBJECT-TYPE
   SYNTAX   INTEGER (0..255)
   ACCESS   read-write
   STATUS   mandatory
   DESCRIPTION
      "<Definition> Preempt Miscellaneous Control Parameter 
       Mask ( Bit=0: False/Disabled, Bit=1: True/Enabled) 
       as follows:
          Bit 7: Reserved
          Bit 6: Reserved
          Bit 5: Reserved
          Bit 4: Reserved

          Bit 3: Flash Dwell - the CU shall cause the 
             phases listed in the preemptDwellPhase object 
             to flash Yellow during the Dwell interval.  All 
             active phases not listed in preemptDwellPhase 
             shall flash Red.
               The CU shall cause the overlaps listed in 
             the preemptDwellOverlap object to flash Yellow 
             during the Dwell state. All active overlaps not 
             listed in preemptDwellOverlap shall flash Red.
             Preempt cycling phase programming is ignored if 
             this bit is set.
             This control is optional.
          Bit 2: Preempt Override preemptNumber + 1 - 
             provide a means to define whether this preempt 
             shall NOT override the next higher numbered 
             Preempt.  When set (1) this preempt shall not 
             override the next higher numbered preempt.
             Lowered numbered preempts override higher 
             numbered preempts. For example, 1 overrides 3,
             and the only way to get 3 equal to 1, is to set
             both 1 and 2 to NOT override the next higher
             numbered preempt.  This parameter shall be 
             ignored when preemptNumber equals maxPreempts.
          Bit 1: Preempt Override Flash - provide a means 
             to define whether this preempt shall NOT 
             override Automatic Flash. When set (1) this 
             preempt shall not override Automatic Flash.
          Bit 0: Non-Locking Memory - provide a means to 
             enable an operation which does not require 
             detector memory. When set (1) a preempt 
             sequence shall not occur if the preempt input 
             terminates prior to expiration of the 
             preemptDelay time.

       A SET of a 'reserved' bit to a value other than 
       zero (0) shall return a badValue(3) error.
       <DescriptiveName> NTCIP-1202::ASC.preemptControl
       <DataConceptType> Data Element"
   REFERENCE
      "NEMA TS 2 Clause 3.7.2.1 and 3.7.2.2"
   DEFVAL   { 0 }
::= { preemptEntry 2 }

-- 2.7.2.3 PREEMPT LINK PARAMETER

preemptLink   OBJECT-TYPE
   SYNTAX   INTEGER (0..255)
   ACCESS   read-write
   STATUS   mandatory
   DESCRIPTION
      "<Definition> This object provides a means to define 
       a higher priority preempt to be combined (linked) 
       with this preempt. At the end of preemptDwellGreen, the 
       linked preempt shall receive an automatic call that 
       shall be maintained as long as the demand for this 
       preempt is active. Any value that is not a higher 
       priority preempt or a valid preempt shall be ignored. 
       The value shall not exceed the maxPreempts object 
       value.
       <DescriptiveName> NTCIP-1202::ASC.preemptLink
       <DataConceptType> Data Element
       <Unit> preempt"
   DEFVAL   { 0 }
::= { preemptEntry 3 }

-- 2.7.2.4 PREEMPT DELAY PARAMETER

preemptDelay   OBJECT-TYPE
   SYNTAX   INTEGER (0..65535)
   ACCESS   read-write
   STATUS   mandatory
   DESCRIPTION
      "<Definition> Preempt Delay Time in seconds (0-600 
       sec). This value determines the time the preempt 
       input shall be active prior to initiating any preempt 
       sequence.  A non-locking preempt input which is 
       removed prior to the completion of this time shall 
       not cause a preempt sequence to occur.
       <DescriptiveName> NTCIP-1202::ASC.preemptDelay
       <DataConceptType> Data Element
       <Unit> second"
   DEFVAL   { 0 }
::= { preemptEntry 4 }

-- 2.7.2.5 PREEMPT DURATION PARAMETER

preemptMinimumDuration   OBJECT-TYPE
   SYNTAX   INTEGER (0..65535)
   ACCESS   read-write
   STATUS   mandatory
   DESCRIPTION
      "<Definition> Preempt Minimum Duration Time in seconds 
       (0..65535 sec). This value determines the minimum time 
       during which the preempt is active. Duration begins 
       timing at the end of Preempt Delay (if non zero) and 
       will prevent an exit from the Dwell interval until 
       this time has elapsed.
       <DescriptiveName> NTCIP-1202::ASC.preemptMinimumDuration
       <DataConceptType> Data Element
       <Unit> second"
   DEFVAL   { 0 }
::= { preemptEntry 5 }

-- 2.7.2.6 PREEMPT MINIMUM GREEN PARAMETER

preemptMinimumGreen   OBJECT-TYPE
   SYNTAX   INTEGER (0..255)
   ACCESS   read-write
   STATUS   mandatory
   DESCRIPTION
      "<Definition> Preempt Minimum Green Time in seconds 
       (0-255 sec). A preempt initiated transition shall 
       not cause the termination of an existing Green prior 
       to its display for lesser of the phase’s Minimum 
       Green time or this period. CAUTION -- if this value 
       is zero, phase Green is terminated immediately.
       <DescriptiveName> NTCIP-1202::ASC.preemptMinimumGreen
       <DataConceptType> Data Element
       <Unit> second"
   DEFVAL   { 255 }
::= { preemptEntry 6 }

-- 2.7.2.7 PREEMPT MINIMUM WALK PARAMETER

preemptMinimumWalk   OBJECT-TYPE
   SYNTAX   INTEGER (0..255)
   ACCESS   read-write
   STATUS   mandatory
   DESCRIPTION
      "<Definition> Preempt Minimum Walk Time in seconds 
       (0-255 sec). A preempt initiated transition shall 
       not cause the termination of an existing Walk prior 
       to its display for the lesser of the phase’s Walk 
       time or this period. CAUTION -- if this value is 
       zero, phase Walk is terminated immediately.
       <DescriptiveName> NTCIP-1202::ASC.preemptMinimumWalk
       <DataConceptType> Data Element
       <Unit> second"
   DEFVAL   { 255 }
::= { preemptEntry 7 }

-- 2.7.2.8 PREEMPT ENTER PEDESTRIAN CLEAR PARAMETER

preemptEnterPedClear   OBJECT-TYPE
   SYNTAX   INTEGER (0..255)
   ACCESS   read-write
   STATUS   mandatory
   DESCRIPTION
      "<Definition> Enter Ped ClearTime in seconds (0-255 
       sec). This parameter controls the ped clear timing 
       for a normal Walk signal terminated by a preempt 
       initiated transition.  A preempt initiated 
       transition shall not cause the termination of a 
       Pedestrian Clearance prior to its display for the 
       lesser of the phase’s Pedestrian Clearance time or 
       this period. CAUTION -- if this value is zero, phase
       Ped Clear is terminated immediately.
       <DescriptiveName> NTCIP-1202::ASC.preemptEnterPedClear
       <DataConceptType> Data Element
       <Unit> second"
   DEFVAL   { 255 }
::= { preemptEntry 8 }

-- 2.7.2.9 PREEMPT TRACK GREEN PARAMETER

preemptTrackGreen   OBJECT-TYPE
   SYNTAX   INTEGER (0..255)
   ACCESS   read-write
   STATUS   mandatory
   DESCRIPTION
      "<Definition> Track Clear Green Time in seconds 
       (0-255 sec). This parameter controls the green 
       timing for the track clearance movement. Track 
       Clear phase(s) are enabled in the preemptTrackPhase
       object. If this value is zero, the track clearance
       movement is omitted, regardless of preemptTrackPhase
       programming.
       <DescriptiveName> NTCIP-1202::ASC.preemptTrackGreen
       <DataConceptType> Data Element
       <Unit> second"
   DEFVAL   { 0 }
::= { preemptEntry 9 }

-- 2.7.2.10 PREEMPT MINIMUM DWELL PARAMETER

preemptDwellGreen   OBJECT-TYPE
   SYNTAX   INTEGER (0..255)
   ACCESS   read-write
   STATUS   mandatory
   DESCRIPTION
      "<Definition> Minimum Dwell interval in seconds (1-255 
       sec). This parameter controls the minimum timing for 
       the dwell interval. Phase(s) active during the 
       Dwell interval are enabled in preemptDwellPhase 
       and preemptCyclingPhase objects.

       The Dwell interval shall not terminate prior to the 
       completion of preemptMinimumDuration, preemptDwellGreen
       (this object), and the call is no longer present.
       <DescriptiveName> NTCIP-1202::ASC.preemptDwellGreen
       <DataConceptType> Data Element
       <Unit> second"
   DEFVAL   { 10 }
::= { preemptEntry 10 }

-- 2.7.2.11 PREEMPT MAXIMUM PRESENCE PARAMETER

preemptMaximumPresence   OBJECT-TYPE
   SYNTAX   INTEGER (0..65535)
   ACCESS   read-write
   STATUS   mandatory
   DESCRIPTION
      "<Definition> Preempt Maximum Presence time in 
       seconds (0-65535 sec). This value determines the 
       maximum time which a preempt call may remain active 
       and be considered valid.  When the preempt call has 
       been active for this time period, the CU shall 
       return to normal operation.  This preempt call shall 
       be considered invalid until such time as a change in 
       state occurs (no longer active).  When set to zero 
       the preempt maximum presence time is disabled.
       <DescriptiveName> NTCIP-1202::ASC.preemptMaximumPresence
       <DataConceptType> Data Element
       <Unit> second"
   DEFVAL   { 0 }
::= { preemptEntry 11 }

-- 2.7.2.12 PREEMPT TRACK PHASE PARAMETER

preemptTrackPhase   OBJECT-TYPE
   SYNTAX   OCTET STRING
   ACCESS   read-write
   STATUS   mandatory
   DESCRIPTION
      "<Definition> Each octet within the octet string 
       contains a phaseNumber(binary value) that shall be 
       active during the Preempt Track Clear intervals.
       The values of phaseNumber used here shall not 
       exceed maxPhases or violate the Consistency Checks 
       defined in Annex B.
       <DescriptiveName> NTCIP-1202::ASC.preemptTrackPhase
       <DataConceptType> Data Element"
   DEFVAL   { "" }
::= { preemptEntry 12 }

-- 2.7.2.13 PREEMPT DWELL PHASE PARAMETER

preemptDwellPhase   OBJECT-TYPE
   SYNTAX   OCTET STRING
   ACCESS   read-write
   STATUS   mandatory
   DESCRIPTION
      "<Definition> Each octet within the octet string 
       contains a phaseNumber (binary value) that 
       specifies the phase(s) to be served in the 
       Preempt Dwell interval. The phase(s) defined in 
       preemptCyclingPhase shall occur after those defined
       herein.
       The values of phaseNumber used here shall not 
       exceed maxPhases or violate the Consistency Checks 
       defined in Annex B.
       <DescriptiveName> NTCIP-1202::ASC.preemptDwellPhase
       <DataConceptType> Data Element"
   DEFVAL   { "" }
::= { preemptEntry 13 }

-- 2.7.2.14 PREEMPT DWELL PED PARAMETER

preemptDwellPed   OBJECT-TYPE
   SYNTAX   OCTET STRING
   ACCESS   read-write
   STATUS   mandatory
   DESCRIPTION
      "<Definition> Each octet within the octet string 
       contains a phaseNumber (binary value) that specifies
       the pedestrian movement(s) to be served in
       the Preempt Dwell interval. The peds defined in
       premptCyclingPed shall occur after those defined
       herein.
       The values of phaseNumber used here shall not 
       exceed maxPhases or violate the Consistency Checks 
       defined in Annex B.

       <DescriptiveName> NTCIP-1202::ASC.preemptDwellPed
       <DataConceptType> Data Element"
   DEFVAL   { "" }
::= { preemptEntry 14 }

-- 2.7.2.15 PREEMPT EXIT PHASE PARAMETER

preemptExitPhase   OBJECT-TYPE
   SYNTAX   OCTET STRING
   ACCESS   read-write
   STATUS   mandatory
   DESCRIPTION
      "<Definition> Each octet within the octet string 
       contains a phaseNumber (binary value) that shall be 
       active following Preempt.
       The values of phaseNumber used here shall not 
       exceed maxPhases or violate the Consistency Checks 
       defined in Annex B.
       <DescriptiveName> NTCIP-1202::ASC.preemptExitPhase
       <DataConceptType> Data Element"
   DEFVAL   { "" }
::= { preemptEntry 15 }

-- 2.7.2.16  PREEMPT STATE

preemptState   OBJECT-TYPE
   SYNTAX   INTEGER { other (1),
                      notActive (2),
                      notActiveWithCall (3),
                      entryStarted (4),
                      trackService (5),
                      dwell (6),
                      linkActive (7),
                      exitStarted (8),
                      maxPresence (9) }
   ACCESS   read-only
   STATUS   mandatory
   DESCRIPTION
      "<Definition> Preempt State provides status on which 
       state the associated preempt is in.  The states are 
       as follows:
          other: preempt service is not specified in this 
             standard.
          notActive: preempt input is not active, this 
             preempt is not active.
          notActiveWithCall: preempt input is active, 
             preempt service has not started.
          entryStarted: preempt service is timing the entry 
             intervals.
          trackService: preempt service is timing the track 
             intervals.
          dwell: preempt service is timing the dwell 
             intervals.
          linkActive: preempt service is performing linked 
             operation.
          exitStarted: preempt service is timing the exit 
             intervals.
          maxPresence: preempt input has exceeded 
             maxPresence time
       <DescriptiveName> NTCIP-1202::ASC.preemptState
       <DataConceptType> Data Element"
::= { preemptEntry 16}

-- 2.7.2.17 PREEMPT TRACK OVERLAP PARAMETER

preemptTrackOverlap   OBJECT-TYPE
   SYNTAX   OCTET STRING
   ACCESS   read-write
   STATUS   mandatory
   DESCRIPTION
      "<Definition> Each octet within the octet string 
       contains a overlapNumber (binary value) that shall 
       be active during the Preempt Track Clear intervals.
       The values of overlapNumber used here shall not 
       exceed maxOverlaps or violate the consistency checks 
       defined in Annex B.
       <DescriptiveName> NTCIP-1202::ASC.preemptTrackOverlap
       <DataConceptType> Data Element"
   DEFVAL   { "" }
::= { preemptEntry 17 }

-- 2.7.2.18 PREEMPT DWELL OVERLAP PARAMETER

preemptDwellOverlap   OBJECT-TYPE
   SYNTAX   OCTET STRING
   ACCESS   read-write
   STATUS   mandatory
   DESCRIPTION
      "<Definition> Each octet within the octet string 
       contains a overlapNumber (binary value) that is 
       allowed during the Preempt Dwell interval.
       The values of overlapNumber used here shall not 
       exceed maxOverlaps or violate the consistency checks 
       defined in Annex B.
       <DescriptiveName> NTCIP-1202::ASC.preemptDwellOverlap
       <DataConceptType> Data Element"
   DEFVAL   { "" }
::= { preemptEntry 18 }

-- 2.7.2.19 PREEMPT CYCLING PHASE PARAMETER

preemptCyclingPhase   OBJECT-TYPE
   SYNTAX   OCTET STRING
   ACCESS   read-write
   STATUS   mandatory
   DESCRIPTION
      "<Definition> Each octet within the octet string 
       contains a phaseNumber (binary value) that is 
       allowed to cycle during the Preempt Dwell interval.
       The values of phaseNumber used here shall not 
       exceed maxPhases or violate the Consistency Checks 
       defined in Annex B.

       <DescriptiveName> NTCIP-1202::ASC.preemptCyclingPhase
       <DataConceptType> Data Element"
   DEFVAL   { "" }
::= { preemptEntry 19 }

-- 2.7.2.20 PREEMPT CYCLING PED PARAMETER

preemptCyclingPed   OBJECT-TYPE
   SYNTAX   OCTET STRING
   ACCESS   read-write
   STATUS   mandatory
   DESCRIPTION
      "<Definition> Each octet within the octet string 
       contains a phaseNumber (binary value) indicating a 
       pedestrian movement that is allowed to cycle during 
       the Preempt Dwell interval.
       The values of phaseNumber used here shall not 
       exceed maxPhases or violate the consistency checks 
       defined in Annex B.
       <DescriptiveName> NTCIP-1202::ASC.preemptCyclingPed
       <DataConceptType> Data Element"
   DEFVAL   { "" }
::= { preemptEntry 20 }

-- 2.7.2.21 PREEMPT CYCLING OVERLAP PARAMETER

preemptCyclingOverlap   OBJECT-TYPE
   SYNTAX   OCTET STRING
   ACCESS   read-write
   STATUS   mandatory
   DESCRIPTION
      "<Definition> Each octet within the octet string 
       contains a overlapNumber (binary value) that is 
       allowed to cycle during the Preempt Dwell interval.
       The values of overlapNumber used here shall not 
       exceed maxOverlaps or violate the consistency checks 
       defined in Annex B.
       <DescriptiveName> NTCIP-1202::ASC.preemptCyclingOverlap
       <DataConceptType> Data Element"
   DEFVAL   { "" }
::= { preemptEntry 21 }

-- 2.7.2.22 PREEMPT ENTER YELLOW CHANGE PARAMETER

preemptEnterYellowChange   OBJECT-TYPE
   SYNTAX   INTEGER (0..255)
   ACCESS   read-write
   STATUS   mandatory
   DESCRIPTION
      "<Definition> Enter Yellow Change in tenth seconds (0-25.5 
       sec). This parameter controls the yellow change
       timing for a normal Yellow Change signal terminated by a
       preempt initiated transition.  A preempt initiated 
       transition shall not cause the termination of a Yellow
       Change prior to its display for the lesser of the phase’s
       Yellow Change time or this period.  CAUTION -- if this
       value is zero, phase Yellow Change is terminated immediately.
       <DescriptiveName> NTCIP-1202::ASC.preemptEnterYellowChange
       <DataConceptType> Data Element
       <Unit> tenth second"
   DEFVAL {255}
::= { preemptEntry 22 }

-- 2.7.2.23 PREEMPT ENTER RED CLEAR PARAMETER

preemptEnterRedClear   OBJECT-TYPE
   SYNTAX   INTEGER (0..255)
   ACCESS   read-write
   STATUS   mandatory
   DESCRIPTION
      "<Definition> Enter Red Clear in tenth seconds (0-25.5 
       sec). This parameter controls the red clearance
       timing for a normal Red Clear signal terminated by a
       preempt initiated transition.  A preempt initiated
       transition shall not cause the termination of a Red 
       Clear prior to its display for the lesser of the phase’s
       Red Clear time or this period.  CAUTION -- if this value is 
       zero, phase Red Clear is terminated immediately.
       <DescriptiveName> NTCIP-1202::ASC.preemptEnterRedClear
       <DataConceptType> Data Element
       <Unit> tenth second"
   DEFVAL {255}
::= { preemptEntry 23 }

-- 2.7.2.24 PREEMPT TRACK YELLOW CHANGE PARAMETER

preemptTrackYellowChange   OBJECT-TYPE
   SYNTAX   INTEGER (0..255)
   ACCESS   read-write
   STATUS   mandatory
   DESCRIPTION
      "<Definition> Track Clear Yellow Change time in tenth
       seconds (0-25.5 sec). The lesser of the phase’s
       Yellow Change time or this parameter controls the
       yellow timing for the track clearance movement. Track
       clear phase(s) are enabled in the preemptTrackPhase object.
       <DescriptiveName> NTCIP-1202::ASC.preemptTrackYellowChange
       <DataConceptType> Data Element
       <Unit> tenth second"
   DEFVAL {255}
::= { preemptEntry 24 }

-- 2.7.2.25 PREEMPT TRACK RED CLEAR PARAMETER

preemptTrackRedClear   OBJECT-TYPE
   SYNTAX   INTEGER (0..255)
   ACCESS   read-write
   STATUS   mandatory
   DESCRIPTION
      "<Definition> Track Clear Red Clear time in tenth seconds
       (0-25.5 sec). The lesser of the phase’s Red Clear
       time or this parameter controls the Red Clear 
       timing for the track clearance movement.  Track clear
       phase(s) are enabled in the preemptTrackPhase object.
       <DescriptiveName> NTCIP-1202::ASC.preemptTrackRedClear
       <DataConceptType> Data Element
       <Unit> tenth second"
   DEFVAL {255}
::= { preemptEntry 25 }

-- 2.7.3 PREEMPT CONTROL TABLE

preemptControlTable   OBJECT-TYPE
   SYNTAX   SEQUENCE OF PreemptControlEntry
   ACCESS   not-accessible
   STATUS   mandatory
   DESCRIPTION
      "<Definition> This table contains the control objects 
       that allow the preempts to be activated remotely.  
       There shall be one control object for each preempt 
       input supported by the device.  The number of rows 
       in this table shall be equal to maxPreempts.
       <TableType> static
       <DescriptiveName> NTCIP-1202::ASC.preemptControlTable
       <DataConceptType> Entity Type"
::= { preempt 3 }

preemptControlEntry   OBJECT-TYPE
   SYNTAX   PreemptControlEntry
   ACCESS   not-accessible
   STATUS   mandatory
   DESCRIPTION
      "<Definition> Control objects for each preempt input. 
       These objects allow the system to activate preempt 
       functions remotely.
       <DescriptiveName> NTCIP-1202::ASC.preemptControlEntry
       <DataConceptType> Entity Type"
   INDEX   { preemptControlNumber }
::= { preemptControlTable 1 }

PreemptControlEntry ::= SEQUENCE { 
   preemptControlNumber   INTEGER,
   preemptControlState    INTEGER }

-- 2.7.3.1 PREEMPT CONTROL NUMBER

preemptControlNumber   OBJECT-TYPE
   SYNTAX   INTEGER (1..255)
   ACCESS   read-only
   STATUS   mandatory
   DESCRIPTION
      "<Definition> This object shall indicate the preempt 
       input number controlled by the associated 
       preemptControlState object in this row.
       <DescriptiveName> NTCIP-1202::ASC.preemptControlNumber
       <DataConceptType> Data Element
       <Unit> preempt"
::= { preemptControlEntry  1 }


-- 2.7.3.2 PREEMPT CONTROL STATE

preemptControlState   OBJECT-TYPE
   SYNTAX   INTEGER (0..1)
   ACCESS   read-write
   STATUS   mandatory
   DESCRIPTION
      "<Definition> This object when set to ON (one) 
       shall cause the associated preempt actions to occur 
       unless the actions have already been started by the 
       physical preempt input. The preempt shall remain 
       active as long as this object is ON or the physical 
       preempt input is ON.  This object when set to OFF 
       (zero) shall cause the physical preempt input to 
       control the associated preempt actions. 

       The device shall reset this object to ZERO when in 
       BACKUP Mode. A write to this object shall reset the 
       Backup timer to ZERO (see unitBackupTime).
       <DescriptiveName> NTCIP-1202::ASC.preemptControlState
       <DataConceptType> Data Element"
::= { preemptControlEntry  2 }

-- 2.8 RING PARAMETERS

ring  OBJECT IDENTIFIER
::= { asc  7 }

-- The ring node contains objects that support ring configuration, 
-- status and control functions in the device.

-- 2.8.1 MAXIMUM RINGS

maxRings   OBJECT-TYPE
   SYNTAX   INTEGER (1..255)
   ACCESS   read-only
   STATUS   mandatory
   DESCRIPTION
      "<Definition> The value of this object shall specify 
       the maximum number of rings this device supports.
       <DescriptiveName> NTCIP-1202::ASC.maxRings
       <DataConceptType> Data Element
       <Unit> ring"
::= { ring 1 }

-- 2.8.2 MAXIMUM SEQUENCES

maxSequences   OBJECT-TYPE
   SYNTAX   INTEGER (1..255)
   ACCESS   read-only
   STATUS   mandatory
   DESCRIPTION
      "<Definition> The value of this object shall specify 
       the maximum number of sequence plans this device 
       supports.
       <DescriptiveName> NTCIP-1202::ASC.maxSequences
       <DataConceptType> Data Element
       <Unit> sequence"
::= { ring 2 }

-- 2.8.3 SEQUENCE TABLE

sequenceTable   OBJECT-TYPE
   SYNTAX   SEQUENCE OF SequenceEntry
   ACCESS   not-accessible
   STATUS   mandatory
   DESCRIPTION
      "<Definition> This table contains all the sequence 
       plans for the controller. A sequence plan shall 
       consist of one row for each ring that the CU 
       supports.  Each row defines the phase service order 
       for that ring.
       <TableType> static
       <DescriptiveName> NTCIP-1202::ASC.sequenceTable
       <DataConceptType> Entity Type"
::= { ring 3 }

sequenceEntry   OBJECT-TYPE
   SYNTAX   SequenceEntry
   ACCESS   not-accessible
   STATUS   mandatory
   DESCRIPTION
      "<Definition> Phase Sequence Parameters for an 
       Actuated Controller Unit.
       <DescriptiveName> NTCIP-1202::ASC.sequenceEntry
       <DataConceptType> Entity Type"
   INDEX   { sequenceNumber, sequenceRingNumber }
::= { sequenceTable 1 }

SequenceEntry ::= SEQUENCE {
   sequenceNumber       INTEGER,
   sequenceRingNumber   INTEGER,
   sequenceData         OCTET STRING }

-- 2.8.3.1 SEQUENCE NUMBER

sequenceNumber  OBJECT-TYPE
   SYNTAX   INTEGER (1..255)
   ACCESS  read-only
   STATUS  mandatory
   DESCRIPTION
      "<Definition> This number identifies a sequence plan. 
       Each row of the table contains the phase sequence 
       for a ring.  A sequence plan shall consist of one 
       row for each ring that defines the phase sequences 
       for that ring.
       <DescriptiveName> NTCIP-1202::ASC.sequenceNumber
       <DataConceptType> Data Element
       <Unit> sequence"
::= { sequenceEntry 1 }


-- 2.8.3.2 SEQUENCE RING NUMBER

sequenceRingNumber  OBJECT-TYPE
   SYNTAX   INTEGER (1..255)
   ACCESS  read-only
   STATUS  mandatory
   DESCRIPTION
      "<Definition> This number identifies the ring number 
       this phase sequence applies to.
       <DescriptiveName> NTCIP-1202::ASC.sequenceRingNumber
       <DataConceptType> Data Element
       <Unit> ring"
::= { sequenceEntry 2 }

-- 2.8.3.3 SEQUENCE DATA

sequenceData   OBJECT-TYPE
   SYNTAX   OCTET STRING
   ACCESS   read-write
   STATUS   mandatory
   DESCRIPTION
      "<Definition> Each octet is a Phase Number (binary 
       value) within the associated ring number.  The phase 
       number value shall not exceed the maxPhases object 
       value.  The order of phase numbers determines the 
       phase sequence for the ring.  The phase numbers 
       shall not be ordered in a manner that would violate 
       the Consistency Checks defined in Annex B.
       <DescriptiveName> NTCIP-1202::ASC.sequenceData
       <DataConceptType> Data Element"
::= { sequenceEntry 3 }

-- 2.8.4 MAXIMUM RING CONTROL GROUPS

maxRingControlGroups   OBJECT-TYPE
   SYNTAX   INTEGER (1..255)
   ACCESS   read-only
   STATUS   mandatory
   DESCRIPTION
      "<Definition> The maximum number of Ring Control 
       Groups (8 rings per group) this Actuated Controller 
       Unit supports.  This value is equal to 
       TRUNCATE[(maxRings + 7) / 8]. This object indicates 
       the maximum rows which shall appear in the 
       ringControlGroupTable object.
       <DescriptiveName> NTCIP-1202::ASC.maxRingControlGroups
       <DataConceptType> Data Element
       <Unit> group"
::= { ring 4 }


-- 2.8.5 RING CONTROL GROUP TABLE

ringControlGroupTable   OBJECT-TYPE
   SYNTAX   SEQUENCE OF RingControlGroupEntry
   ACCESS   not-accessible
   STATUS   mandatory
   DESCRIPTION
      "<Definition> A table containing Actuated Controller 
       Unit Ring Control in groups of eight rings. The 
       number of rows in this table is equal to the 
       maxRingControlGroups object.
       <TableType> static
       <DescriptiveName> NTCIP-1202::ASC.ringControlGroupTable
       <DataConceptType> Entity Type"
::= { ring 5 }

ringControlGroupEntry   OBJECT-TYPE
   SYNTAX   RingControlGroupEntry
   ACCESS   not-accessible
   STATUS   mandatory
   DESCRIPTION
      "<Definition> Ring Control for eight Actuated 
       Controller Unit rings.
       <DescriptiveName> NTCIP-1202::ASC.ringControlGroupEntry
       <DataConceptType> Entity Type"
   INDEX   { ringControlGroupNumber }
::= { ringControlGroupTable 1 }

RingControlGroupEntry ::= SEQUENCE { 
   ringControlGroupNumber         INTEGER,
   ringControlGroupStopTime       INTEGER,
   ringControlGroupForceOff       INTEGER,
   ringControlGroupMax2           INTEGER,
   ringControlGroupMaxInhibit     INTEGER,
   ringControlGroupPedRecycle     INTEGER,
   ringControlGroupRedRest        INTEGER,
   ringControlGroupOmitRedClear   INTEGER }

-- 2.8.5.1 RING CONTROL GROUP NUMBER

ringControlGroupNumber   OBJECT-TYPE
   SYNTAX   INTEGER (1..255)
   ACCESS   read-only
   STATUS   mandatory
   DESCRIPTION
      "<Definition> The Ring Control Group number for 
       objects in this row. This value shall not exceed the 
       maxRingControlGroups object value.
       <DescriptiveName> NTCIP-1202::ASC.ringControlGroupNumber
       <DataConceptType> Data Element
       <Unit> group"
::= { ringControlGroupEntry 1 }


-- 2.8.5.2 RING STOP TIME CONTROL

ringControlGroupStopTime   OBJECT-TYPE
   SYNTAX   INTEGER (0..255)
   ACCESS   read-write
   STATUS   mandatory
   DESCRIPTION
      "<Definition> This object is used to allow a remote 
       entity to stop timing in the device. The device 
       shall activate/deactivate the System Stop Time 
       control for a ring according to the respective bit 
       value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupStopTime
       <DataConceptType> Data Element"
   REFERENCE
      "NEMA TS 2 Clause 3.5.4.1.6"
::= { ringControlGroupEntry 2 }

-- 2.8.5.3 RING FORCE OFF CONTROL

ringControlGroupForceOff   OBJECT-TYPE
   SYNTAX   INTEGER (0..255)
   ACCESS   read-write
   STATUS   mandatory
   DESCRIPTION
      "<Definition> This object is used to allow a remote 
       entity to terminate phases via a force off command 
       in the device. The device shall activate/deactivate 
       the System Force Off control for a ring according 
       to the respective bit value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).

       <DescriptiveName> NTCIP-1202::ASC.ringControlGroupForceOff
       <DataConceptType> Data Element"
   REFERENCE
      "NEMA TS 2 Clause 3.5.4.1.1"
::= { ringControlGroupEntry 3 }

-- 2.8.5.4 RING MAX 2 CONTROL

ringControlGroupMax2   OBJECT-TYPE
   SYNTAX   INTEGER (0..255)
   ACCESS   read-write
   STATUS   mandatory
   DESCRIPTION
      "<Definition> This object is used to allow a remote 
       entity to request Maximum 2 timings in the device. 
       The device shall activate/deactivate the System 
       Maximum 2 control for a ring according to the 
       respective bit value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupMax2
       <DataConceptType> Data Element"
   REFERENCE
      "NEMA TS 2 Clause 3.5.4.1.7"
::= { ringControlGroupEntry 4 }

-- 2.8.5.5 RING MAX INHIBIT CONTROL

ringControlGroupMaxInhibit   OBJECT-TYPE
   SYNTAX   INTEGER (0..255)
   ACCESS   read-write
   STATUS   mandatory
   DESCRIPTION
      "<Definition> This object is used to allow a remote 
       entity to request internal maximum timings be 
       inhibited in the device. The device shall 
       activate/deactivate the System Max Inhibit control 
       for a ring according to the respective bit value as 
       follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupMaxInhibit
       <DataConceptType> Data Element"
   REFERENCE
      "NEMA TS 2 Clause 3.5.4.1.3"
::= { ringControlGroupEntry 5 }

-- 2.8.5.6 RING PED RECYCLE CONTROL

ringControlGroupPedRecycle   OBJECT-TYPE
   SYNTAX   INTEGER (0..255)
   ACCESS   read-write
   STATUS   mandatory
   DESCRIPTION
      "<Definition> This object is used to allow a remote 
       entity to request a pedestrian recycle in the 
       device. The device shall activate/deactivate the 
       System Ped Recycle control for a ring according to 
       the respective bit value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupPedRecycle
       <DataConceptType> Data Element"
   REFERENCE
      "NEMA TS 2 Clause 3.5.4.1.5"
::= { ringControlGroupEntry 6 }

-- 2.8.5.7 RING RED REST CONTROL

ringControlGroupRedRest   OBJECT-TYPE
   SYNTAX   INTEGER (0..255)
   ACCESS   read-write
   STATUS   mandatory
   DESCRIPTION
      "<Definition> This object is used to allow a remote 
       entity to request red rest in the device. The 
       device shall activate/deactivate the System Red 
       Rest control for a ring according to the 
       respective bit value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupRedRest
       <DataConceptType> Data Element"
   REFERENCE
      "NEMA TS 2 Clause 3.5.4.1.2"
::= { ringControlGroupEntry 7 }

-- 2.8.5.8 RING OMIT RED CONTROL

ringControlGroupOmitRedClear   OBJECT-TYPE
   SYNTAX   INTEGER (0..255)
   ACCESS   read-write
   STATUS   mandatory
   DESCRIPTION
      "<Definition> This object is used to allow a remote 
       entity to omit red clearances in the device. The 
       device shall activate/deactivate the System Omit 
       Red Clear control for a ring according to the 
       respective bit value as follows:
             bit = 0 - deactivate the ring control
             bit = 1 - activate the ring control
          Bit 7: Ring # = (ringControlGroupNumber * 8)
          Bit 6: Ring # = (ringControlGroupNumber * 8) - 1
          Bit 5: Ring # = (ringControlGroupNumber * 8) - 2
          Bit 4: Ring # = (ringControlGroupNumber * 8) - 3
          Bit 3: Ring # = (ringControlGroupNumber * 8) - 4
          Bit 2: Ring # = (ringControlGroupNumber * 8) - 5
          Bit 1: Ring # = (ringControlGroupNumber * 8) - 6
          Bit 0: Ring # = (ringControlGroupNumber * 8) - 7
       The device shall reset this object to ZERO when in 
       BACKUP Mode. A write to this object shall reset the 
       Backup timer to ZERO (see unitBackupTime).
       <DescriptiveName> NTCIP-1202::ASC.ringControlGroupOmitRedClear
       <DataConceptType> Data Element"
   REFERENCE
      "NEMA TS 2 Clause 3.5.4.1.4"
::= { ringControlGroupEntry 8 }

-- 2.8.6 RING STATUS TABLE

ringStatusTable   OBJECT-TYPE
   SYNTAX   SEQUENCE OF RingStatusEntry
   ACCESS   not-accessible
   STATUS   mandatory
   DESCRIPTION
      "<Definition> A table containing Actuated Controller 
       Unit Ring Status.The number of rows in this table is 
       equal to the maxRings object.
       <TableType> static
       <DescriptiveName> NTCIP-1202::ASC.ringStatusTable
       <DataConceptType> Entity Type"
::= { ring 6 }

ringStatusEntry   OBJECT-TYPE
   SYNTAX   RingStatusEntry
   ACCESS   not-accessible
   STATUS   mandatory
   DESCRIPTION
      "<Definition> Ring Status for an Actuated Controller 
       Unit ring.
       <DescriptiveName> NTCIP-1202::ASC.ringStatusEntry
       <DataConceptType> Entity Type"
   INDEX   { sequenceRingNumber }
::= { ringStatusTable 1 }

RingStatusEntry ::= SEQUENCE { 
   ringStatus   INTEGER }

-- 2.8.6.1 RING STATUS

ringStatus   OBJECT-TYPE
   SYNTAX   INTEGER (0..255)
   ACCESS   read-only
   STATUS   mandatory
   DESCRIPTION
      "<Definition> The Ring Status for this ring.
          Bit 7: Reserved (always zero)
          Bit 6: Reserved (always zero)
          Bit 5: Force Off - When bit = 1, the active 
             phase in the ring was terminated by Force Off
          Bit 4: Max Out - When bit = 1, the active 
             phase in the ring was terminated by Max Out
          Bit 3: Gap Out - When bit = 1, the active 
             phase in the ring was terminated by Gap Out
          Bit 2: Coded Status Bit C
          Bit 1: Coded Status Bit B
          Bit 0: Coded Status Bit A
             +------+-----+-----+-----+---------------+
             | Code |    Bit States   | State         |
             |  ##  |  A  |  B  |  C  | Names         |
             +------+-----+-----+-----+---------------+
             |   0  |  0  |  0  |  0  | Min Green     |
             |   1  |  1  |  0  |  0  | Extension     |
             |   2  |  0  |  1  |  0  | Maximum       |
             |   3  |  1  |  1  |  0  | Green Rest    |
             |   4  |  0  |  0  |  1  | Yellow Change |
             |   5  |  1  |  0  |  1  | Red Clearance |
             |   6  |  0  |  1  |  1  | Red Rest      |
             |   7  |  1  |  1  |  1  | Undefined     |
             +------+-----+-----+-----+---------------+
          NEMA TS 2 Clause 3.5.4.2 provides further
          definition of Coded Status Bits.
       <DescriptiveName> NTCIP-1202::ASC.ringStatus
       <DataConceptType> Data Element"
::= { ringStatusEntry 1 }
-- 2.9 CHANNEL PARAMETERS

channel OBJECT IDENTIFIER 
::= { asc 8 }

--This defines a node for supporting channel objects.

-- 2.9.1 MAXIMUM CHANNELS

maxChannels   OBJECT-TYPE
   SYNTAX   INTEGER (1..255)
   ACCESS   read-only
   STATUS   mandatory
   DESCRIPTION
      "<Definition> The Maximum Number of Channels this 
       Actuated Controller Unit supports. This object 
       indicates the maximum rows which shall appear in the 
       channelTable object.
       <DescriptiveName> NTCIP-1202::ASC.maxChannels
       <DataConceptType> Data Element
       <Unit> channel"
::= { channel 1 }

-- 2.9.2 CHANNEL TABLE

channelTable   OBJECT-TYPE
   SYNTAX   SEQUENCE OF ChannelEntry
   ACCESS   not-accessible
   STATUS   mandatory
   DESCRIPTION
      "<Definition> A table containing Actuated Controller 
       Unit channel parameters. The number of rows in this 
       table is equal to the maxChannels object.
       <TableType> static
       <DescriptiveName> NTCIP-1202::ASC.channelTable
       <DataConceptType> Entity Type"
::= { channel 2 }

channelEntry   OBJECT-TYPE
   SYNTAX   ChannelEntry
   ACCESS   not-accessible
   STATUS   mandatory
   DESCRIPTION
      "<Definition> Parameters for a specific Actuated 
       Controller Unit channel.
       <DescriptiveName> NTCIP-1202::ASC.channelEntry
       <DataConceptType> Entity Type"
   INDEX   { channelNumber }
::= { channelTable 1 }

ChannelEntry ::= SEQUENCE { 
   channelNumber          INTEGER,
   channelControlSource   INTEGER,
   channelControlType     INTEGER,
   channelFlash           INTEGER,
   channelDim             INTEGER }

-- 2.9.2.1 CHANNEL NUMBER

channelNumber   OBJECT-TYPE
   SYNTAX   INTEGER (1..255)
   ACCESS   read-only
   STATUS   mandatory
   DESCRIPTION
      "<Definition> The channel number for objects in this 
       row. This value shall not exceed the maxChannels 
       object value.
       <DescriptiveName> NTCIP-1202::ASC.channelNumber
       <DataConceptType> Data Element
       <Unit> channel"
::= { channelEntry 1 }

-- 2.9.2.2 CHANNEL CONTROL SOURCE PARAMETER

channelControlSource   OBJECT-TYPE
   SYNTAX   INTEGER (0..255)
   ACCESS   read-write
   STATUS   mandatory
   DESCRIPTION
      "<Definition> This object defines the channel control 
       source (which Phase or Overlap). The value shall not 
       exceed maxPhases or maxOverlaps as determined by 
       channelControlType object:
          Value 00 = No Control (Not In Use)
          Value 01 = Phase 01 or Overlap A
          Value 02 = Phase 02 or Overlap B
                        ||
          Value 15 = Phase 15 or Overlap O
          Value 16 = Phase 16 or Overlap P
                       etc.
       <DescriptiveName> NTCIP-1202::ASC.channelControlSource
       <DataConceptType> Data Element"
::= { channelEntry 2 }

-- 2.9.2.3 CHANNEL CONTROL TYPE PARAMETER

channelControlType   OBJECT-TYPE
   SYNTAX   INTEGER { other (1),
                      phaseVehicle (2),
                      phasePedestrian (3),
                      overlap (4) }
   ACCESS   read-write
   STATUS   mandatory
   DESCRIPTION
      "<Definition> This object defines the channel control 
       type (Vehicle Phase, Pedestrian Phase, or Overlap):
         other: The channel controls an other type of 
            display.
         phaseVehicle: The channel controls a vehicle phase 
               display.
         phasePedestrian: The channel controls a pedestrian 
               phase display.
         overlap: The channel controls an overlap display.
       <DescriptiveName> NTCIP-1202::ASC.channelControlType
       <DataConceptType> Data Element"
::= { channelEntry 3 }

-- 2.9.2.4 CHANNEL FLASH PARAMETER

channelFlash   OBJECT-TYPE
   SYNTAX   INTEGER (0..255)
   ACCESS   read-write
   STATUS   mandatory
   DESCRIPTION
      "<Definition> This object defines the channel state 
       during Automatic Flash. 
          Bit 7: Reserved
          Bit 6: Reserved
          Bit 5: Reserved
          Bit 4: Reserved
          Bit 3: Flash Alternate Half Hertz 
             Bit=0: Off/Disabled & Bit=1: On/Enabled
          Bit 2: Flash Red 
             Bit=0: Off/Red Dark & Bit=1: On/Flash Red
          Bit 1: Flash Yellow 
             Bit=0: Off/Yellow Dark & Bit=1: On/Flash Yellow
          Bit 0: Reserved
       A SET of both bits 1 & 2 shall result in bit 1=0 and 
       bit 2=1.
       A SET of a 'reserved' bit to a value other than 
       zero (0) shall return a badValue(3) error.
       <DescriptiveName> NTCIP-1202::ASC.channelFlash
       <DataConceptType> Data Element"
::= { channelEntry 4 }

-- 2.9.2.5 CHANNEL DIM PARAMETER

channelDim   OBJECT-TYPE
   SYNTAX   INTEGER (0..255)
   ACCESS   read-write
   STATUS   mandatory
   DESCRIPTION
      "<Definition> This object defines the channel state 
       during Dimming. Dimming shall be accomplished by the 
       elimination of alternate one-half segments from the 
       AC sinusoid applied to the field terminals. 
          Bit 7: Reserved
          Bit 6: Reserved
          Bit 5: Reserved
          Bit 4: Reserved
          Bit 3: Dim Alternate Half Line Cycle 
             Bit=0: Off/+ half cycle & 
             Bit=1: On/- half cycle
          Bit 2: Dim Red 
             Bit=0: Off/Red Not Dimmed & 
             Bit=1: On/Dimmed Red
          Bit 1: Dim Yellow 
             Bit=0: Off / Yellow Not Dimmed & 
             Bit=1: On / Dimmed Yellow

          Bit 0: Dim Green 
             Bit=0: Off / Green Not Dimmed & 
             Bit=1: On / Dimmed Green
       A SET of a 'reserved' bit to a value other than 
       zero (0) shall return a badValue(3) error.
       <DescriptiveName> NTCIP-1202::ASC.channelDim
       <DataConceptType> Data Element"
::= { channelEntry 5 }

-- 2.9.3 MAXIMUM CHANNEL STATUS GROUPS

maxChannelStatusGroups   OBJECT-TYPE
   SYNTAX   INTEGER (1..255)
   ACCESS   read-only
   STATUS   mandatory
   DESCRIPTION
      "<Definition> The maximum number of Channel Status 
       Groups (8 channels per group) this Actuated 
       Controller Unit supports. This value is equal to 
       TRUNCATE [(maxChannels + 7) / 8]. This object 
       indicates the maximum rows which shall appear in 
       the channelStatusGroupTable object.
       <DescriptiveName> NTCIP-1202::ASC.maxChannelStatusGroups
       <DataConceptType> Data Element
       <Unit> group"
::= { channel 3 }

-- 2.9.4 CHANNEL STATUS GROUP TABLE

channelStatusGroupTable   OBJECT-TYPE
   SYNTAX   SEQUENCE OF ChannelStatusGroupEntry
   ACCESS   not-accessible
   STATUS   mandatory
   DESCRIPTION
      "<Definition> A table containing Actuated Controller 
       Unit channel output (Red, Yellow, & Green) status in 
       groups of eight channels. The number of rows in this 
       table is equal to the maxChannelStatusGroups object.
       <TableType> static
       <DescriptiveName> NTCIP-1202::ASC.channelStatusGroupTable
       <DataConceptType> Entity Type"
::= { channel 4 }

channelStatusGroupEntry   OBJECT-TYPE
   SYNTAX   ChannelStatusGroupEntry
   ACCESS   not-accessible
   STATUS   mandatory
   DESCRIPTION
      "<Definition> Red, Yellow, & Green Output Status for 
       eight Actuated Controller Unit channels.
       <DescriptiveName> NTCIP-1202::ASC.channelStatusGroupEntry
       <DataConceptType> Entity Type"
   INDEX   { channelStatusGroupNumber }
::= { channelStatusGroupTable 1 }


ChannelStatusGroupEntry ::= SEQUENCE { 
   channelStatusGroupNumber    INTEGER,
   channelStatusGroupReds      INTEGER,
   channelStatusGroupYellows   INTEGER,
   channelStatusGroupGreens    INTEGER }

-- 2.9.4.1 CHANNEL STATUS GROUP NUMBER

channelStatusGroupNumber   OBJECT-TYPE
   SYNTAX   INTEGER (1..255)
   ACCESS   read-only
   STATUS   mandatory
   DESCRIPTION
      "<Definition> The channelStatusGroup number for 
       objects in this row. This value shall not exceed the 
       maxChannelStatusGroups object value.
       <DescriptiveName> NTCIP-1202::ASC.channelStatusGroupNumber
       <DataConceptType> Data Element
       <Unit> group"
::= { channelStatusGroupEntry 1 }

-- 2.9.4.2 CHANNEL STATUS GROUP REDS

channelStatusGroupReds   OBJECT-TYPE
   SYNTAX   INTEGER (0..255)
   ACCESS   read-only
   STATUS   mandatory
   DESCRIPTION
      "<Definition> Channel Red Output Status Mask, when a 
       bit=1, the Channel Red is currently active. When a 
       bit=0, the Channel Red is NOT currently active. 
          Bit 7: Channel # = (channelStatusGroupNumber * 8)
          Bit 6: Channel # = (channelStatusGroupNumber * 8) - 1
          Bit 5: Channel # = (channelStatusGroupNumber * 8) - 2
          Bit 4: Channel # = (channelStatusGroupNumber * 8) - 3
          Bit 3: Channel # = (channelStatusGroupNumber * 8) - 4
          Bit 2: Channel # = (channelStatusGroupNumber * 8) - 5
          Bit 1: Channel # = (channelStatusGroupNumber * 8) - 6
          Bit 0: Channel # = (channelStatusGroupNumber * 8) - 7
       <DescriptiveName> NTCIP-1202::ASC.channelStatusGroupReds
       <DataConceptType> Data Element"
::= { channelStatusGroupEntry 2 }

-- 2.9.4.3 CHANNEL STATUS GROUP YELLOWS

channelStatusGroupYellows   OBJECT-TYPE
   SYNTAX   INTEGER (0..255)
   ACCESS   read-only
   STATUS   mandatory
   DESCRIPTION
      "<Definition> Channel Yellow Output Status Mask, when 
       a bit=1, the Channel Yellow is currently active. When 
       a bit=0, the Channel Yellow is NOT currently active.
          Bit 7: Channel # = (channelStatusGroupNumber * 8)
          Bit 6: Channel # = (channelStatusGroupNumber * 8) - 1
          Bit 5: Channel # = (channelStatusGroupNumber * 8) - 2
          Bit 4: Channel # = (channelStatusGroupNumber * 8) - 3
          Bit 3: Channel # = (channelStatusGroupNumber * 8) - 4
          Bit 2: Channel # = (channelStatusGroupNumber * 8) - 5
          Bit 1: Channel # = (channelStatusGroupNumber * 8) - 6
          Bit 0: Channel # = (channelStatusGroupNumber * 8) - 7
       <DescriptiveName> NTCIP-1202::ASC.channelStatusGroupYellows
       <DataConceptType> Data Element"
::= { channelStatusGroupEntry 3 }

-- 2.9.4.4 CHANNEL STATUS GROUP GREENS

channelStatusGroupGreens   OBJECT-TYPE
   SYNTAX   INTEGER (0..255)
   ACCESS   read-only
   STATUS   mandatory
   DESCRIPTION
      "<Definition> Channel Green Output Status Mask, when 
       a bit=1, the Channel Green is currently active. When 
       a bit=0, the Channel Green is NOT currently active.
          Bit 7: Channel # = (channelStatusGroupNumber * 8)
          Bit 6: Channel # = (channelStatusGroupNumber * 8) - 1
          Bit 5: Channel # = (channelStatusGroupNumber * 8) - 2
          Bit 4: Channel # = (channelStatusGroupNumber * 8) - 3
          Bit 3: Channel # = (channelStatusGroupNumber * 8) - 4
          Bit 2: Channel # = (channelStatusGroupNumber * 8) - 5
          Bit 1: Channel # = (channelStatusGroupNumber * 8) - 6
          Bit 0: Channel # = (channelStatusGroupNumber * 8) - 7
       <DescriptiveName> NTCIP-1202::ASC.channelStatusGroupGreens
       <DataConceptType> Data Element"
::= { channelStatusGroupEntry 4 }

-- 2.10 OVERLAP PARAMETERS

overlap   OBJECT IDENTIFIER
::= { asc 9 }

--"This node contains objects that configure, monitor and 
-- control overlap functions."

-- 2.10.1 MAXIMUM OVERLAPS

maxOverlaps   OBJECT-TYPE
   SYNTAX   INTEGER (1..255)
   ACCESS   read-only
   STATUS   mandatory
   DESCRIPTION
      "<Definition> The Maximum Number of Overlaps this 
       Actuated Controller Unit supports. This object 
       indicates the maximum number of rows which shall 
       appear in the overlapTable object.
       <DescriptiveName> NTCIP-1202::ASC.maxOverlaps
       <DataConceptType> Data Element
       <Unit> overlap"
::= { overlap 1 }


-- 2.10.2 OVERLAP TABLE

overlapTable   OBJECT-TYPE
   SYNTAX   SEQUENCE OF OverlapEntry
   ACCESS   not-accessible
   STATUS   mandatory
   DESCRIPTION
      "<Definition> A table containing Actuated Controller 
       Unit overlap parameters. The number of rows in this 
       table is equal to the maxOverlaps object.
       <TableType> static
       <DescriptiveName> NTCIP-1202::ASC.overlapTable
       <DataConceptType> Entity Type"
::= { overlap 2 }

overlapEntry   OBJECT-TYPE
   SYNTAX   OverlapEntry
   ACCESS   not-accessible
   STATUS   mandatory
   DESCRIPTION
      "<Definition> Parameters for a specific Actuated 
       Controller Unit overlap.
       <DescriptiveName> NTCIP-1202::ASC.overlapEntry
       <DataConceptType> Entity Type"
   INDEX   { overlapNumber }
::= { overlapTable 1 }

OverlapEntry ::= SEQUENCE { 
   overlapNumber           INTEGER,
   overlapType             INTEGER,
   overlapIncludedPhases   OCTET STRING,
   overlapModifierPhases   OCTET STRING,
   overlapTrailGreen       INTEGER,
   overlapTrailYellow      INTEGER,
   overlapTrailRed         INTEGER }

-- 2.10.2.1 OVERLAP NUMBER

overlapNumber   OBJECT-TYPE
   SYNTAX  INTEGER (1..255)
   ACCESS   read-only
   STATUS   mandatory
   DESCRIPTION
      "<Definition> The overlap number for objects in this 
       row. The value shall not exceed the maxOverlaps 
       object. The value maps to the Overlap as follows: 
       1 = Overlap A, 2 = Overlap B etc.
       <DescriptiveName> NTCIP-1202::ASC.overlapNumber
       <DataConceptType> Data Element
       <Unit> overlap"
::= { overlapEntry 1 }


-- 2.10.2.2 OVERLAP TYPE

overlapType   OBJECT-TYPE
   SYNTAX   INTEGER { other(1),
                      normal (2),
                      minusGreenYellow (3) }
   ACCESS   read-only
   STATUS   mandatory
   DESCRIPTION
      "<Definition> The type of overlap operation for this 
       row.  The types are as follows:
         other: The overlap operates in another mode than 
            those described herein.
         normal: The overlap output shall be controlled by 
            the overlapIncludedPhases when this type is 
            indicated. The overlap output shall be green in 
            the following situations:
               (1) when an overlap included phase is green.
               (2) when an overlap included phase is yellow 
                   (or red clearance) and an overlap 
                   included phase is next.

            The overlap output shall be yellow when an 
            included phase is yellow and an overlap included 
            phase is not next. The overlap output shall be 
            red whenever the overlap green and yellow are 
            not ON.
         minusGreenYellow: The overlap output shall be 
            controlled by the overlapIncludedPhases and the 
            overlapModifierPhases if this type is indicated. 
            The overlap output shall be green in the 
            following situations:
              (1) when an overlap included phase is green 
                  and an overlap modifier phase is NOT green.
              (2) when an overlap included phase is yellow 
                  (or red clearance) and an overlap included 
                  phase is next and an overlap modifier 
                  phase is NOT green.

            The overlap output shall be yellow when an 
            overlap included phase is yellow and an overlap 
            modifier phase is NOT yellow and an overlap 
            included phase is not next. The overlap output 
            shall be red whenever the overlap green and 
            yellow are not ON.
       <DescriptiveName> NTCIP-1202::ASC.overlapType
       <DataConceptType> Data Element"
::= { overlapEntry 2 }


-- 2.10.2.3 OVERLAP INCLUDED PHASE PARAMETER

overlapIncludedPhases   OBJECT-TYPE
   SYNTAX   OCTET STRING
   ACCESS   read-write
   STATUS   mandatory
   DESCRIPTION
      "<Definition> Each octet is a Phase (number) that 
       shall be an included phase for the overlap. The 
       phase number value shall not exceed the maxPhases 
       object value. When an included phase output is green 
       or when the CU is cycling between included phases, 
       the overlap output shall be green.
       <DescriptiveName> NTCIP-1202::ASC.overlapIncludedPhases
       <DataConceptType> Data Element"
::= { overlapEntry 3 }

-- 2.10.2.4 OVERLAP MODIFIER PHASE PARAMETER

overlapModifierPhases   OBJECT-TYPE
   SYNTAX   OCTET STRING
   ACCESS   read-write
   STATUS   mandatory
   DESCRIPTION
      "<Definition> Each octet is a Phase (number) that 
       shall be a modifier phase for the overlap. The phase 
       number value shall not exceed the maxPhases object 
       value.

       A null value provides a normal overlap type. A 
       non-null value provides a minusGreenYellow overlap 
       type.
       <DescriptiveName> NTCIP-1202::ASC.overlapModifierPhases
       <DataConceptType> Data Element"
::= { overlapEntry 4 }

-- 2.10.2.5 OVERLAP TRAILING GREEN PARAMETER

overlapTrailGreen   OBJECT-TYPE
   SYNTAX   INTEGER (0..255)
   ACCESS   read-write
   STATUS   mandatory
   DESCRIPTION
      "<Definition> Overlap Trailing Green Parameter in  
       seconds (0-255 sec). When this value is greater than 
       zero and the overlap green would normally terminate, 
       the overlap green shall be extended by this 
       additional time.
       <DescriptiveName> NTCIP-1202::ASC.overlapTrailGreen
       <DataConceptType> Data Element
       <Unit> second"
::= { overlapEntry 5 }


-- 2.10.2.6 OVERLAP TRAILING YELLOW CHANGE PARAMETER

overlapTrailYellow   OBJECT-TYPE
   SYNTAX  INTEGER (0..255)
   ACCESS   read-write
   STATUS   mandatory
   DESCRIPTION
      "<Definition> Overlap Trailing Yellow Change Parameter 
       in tenth seconds (NEMA range: 3.0-25.5 sec). When 
       the overlap green has been extended (Trailing Green), 
       this value shall determine the current length of the 
       Yellow Change interval for the overlap.
       <DescriptiveName> NTCIP-1202::ASC.overlapTrailYellow
       <DataConceptType> Data Element
       <Unit> tenth second"
::= { overlapEntry 6 }

-- 2.10.2.7 OVERLAP TRAILING RED CLEAR PARAMETER

overlapTrailRed   OBJECT-TYPE
   SYNTAX   INTEGER (0..255)
   ACCESS   read-write
   STATUS   mandatory
   DESCRIPTION
      "<Definition> Overlap Trailing Red Clear Parameter in 
       tenth seconds (0-25.5 sec). When the overlap green 
       has been extended (Trailing Green), this value shall 
       determine the current length of the Red Clearance 
       interval for the overlap.
       <DescriptiveName> NTCIP-1202::ASC.overlapTrailRed
       <DataConceptType> Data Element
       <Unit> tenth second"
::= { overlapEntry 7 }

-- 2.10.3 MAXIMUM OVERLAP STATUS GROUPS

maxOverlapStatusGroups   OBJECT-TYPE
   SYNTAX   INTEGER (1..255)
   ACCESS   read-only
   STATUS   mandatory
   DESCRIPTION
      "<Definition> The Maximum Number of Overlap Status 
       Groups (8 overlaps per group) this Actuated 
       Controller Unit supports. This value is equal to 
       TRUNCATE [(maxOverlaps + 7) / 8]. This object 
       indicates the maximum rows which shall appear in the 
       overlapStatusGroupTable object.
       <DescriptiveName> NTCIP-1202::ASC.maxOverlapStatusGroups
       <DataConceptType> Data Element
       <Unit> group"
::= { overlap 3 }


-- 2.10.4 OVERLAP STATUS GROUP TABLE

overlapStatusGroupTable   OBJECT-TYPE
   SYNTAX   SEQUENCE OF OverlapStatusGroupEntry
   ACCESS   not-accessible
   STATUS   mandatory
   DESCRIPTION
      "<Definition> A table containing Actuated Controller 
       Unit overlap output (Red, Yellow, & Green) status in 
       groups of eight overlaps. The number of rows in this 
       table is equal to the maxOverlapStatusGroups object.
       <TableType> static
       <DescriptiveName> NTCIP-1202::ASC.overlapStatusGroupTable
       <DataConceptType> Entity Type"
::= { overlap 4 }

overlapStatusGroupEntry   OBJECT-TYPE
   SYNTAX   OverlapStatusGroupEntry
   ACCESS   not-accessible
   STATUS   mandatory
   DESCRIPTION
      "<Definition> Red, Yellow, & Green Output Status for 
       eight Actuated Controller Unit overlaps.
       <DescriptiveName> NTCIP-1202::ASC.overlapStatusGroupEntry
       <DataConceptType> Entity Type"
   INDEX   { overlapStatusGroupNumber }
::= { overlapStatusGroupTable 1 }

OverlapStatusGroupEntry ::= SEQUENCE { 
   overlapStatusGroupNumber    INTEGER,
   overlapStatusGroupReds      INTEGER,
   overlapStatusGroupYellows   INTEGER,
   overlapStatusGroupGreens    INTEGER }

-- 2.10.4.1 OVERLAP STATUS GROUP NUMBER

overlapStatusGroupNumber   OBJECT-TYPE
   SYNTAX   INTEGER (1..255)
   ACCESS   read-only
   STATUS   mandatory
   DESCRIPTION
      "<Definition> The overlap StatusGroup number for 
       objects in this row. This value shall not exceed the 
       maxOverlapStatusGroups object value.
       <DescriptiveName> NTCIP-1202::ASC.overlapStatusGroupNumber
       <DataConceptType> Data Element
       <Unit> group"
::= { overlapStatusGroupEntry 1 }


-- 2.10.4.2 OVERLAP STATUS GROUP REDS

overlapStatusGroupReds   OBJECT-TYPE
   SYNTAX   INTEGER (0..255)
   ACCESS   read-only
   STATUS   mandatory
   DESCRIPTION
      "<Definition> Overlap Red Output Status Mask, when a 
       bit=1, the Overlap Red is currently active. When a 
       bit=0, the Overlap Red is NOT currently active.
          Bit 7: Overlap # = (overlapStatusGroupNumber * 8)
          Bit 6: Overlap # = (overlapStatusGroupNumber * 8) - 1
          Bit 5: Overlap # = (overlapStatusGroupNumber * 8) - 2
          Bit 4: Overlap # = (overlapStatusGroupNumber * 8) - 3
          Bit 3: Overlap # = (overlapStatusGroupNumber * 8) - 4
          Bit 2: Overlap # = (overlapStatusGroupNumber * 8) - 5
          Bit 1: Overlap # = (overlapStatusGroupNumber * 8) - 6
          Bit 0: Overlap # = (overlapStatusGroupNumber * 8) - 7
       <DescriptiveName> NTCIP-1202::ASC.overlapStatusGroupReds
       <DataConceptType> Data Element"
::= { overlapStatusGroupEntry 2 }

-- 2.10.4.3 OVERLAP STATUS GROUP YELLOWS

overlapStatusGroupYellows   OBJECT-TYPE
   SYNTAX   INTEGER (0..255)
   ACCESS   read-only
   STATUS   mandatory
   DESCRIPTION
      "<Definition> Overlap Yellow Output Status Mask, when 
       a bit=1, the Overlap Yellow is currently active. When 
       a bit=0, the Overlap Yellow is NOT currently active.
          Bit 7: Overlap # = (overlapStatusGroupNumber * 8)
          Bit 6: Overlap # = (overlapStatusGroupNumber * 8) - 1
          Bit 5: Overlap # = (overlapStatusGroupNumber * 8) - 2
          Bit 4: Overlap # = (overlapStatusGroupNumber * 8) - 3
          Bit 3: Overlap # = (overlapStatusGroupNumber * 8) - 4
          Bit 2: Overlap # = (overlapStatusGroupNumber * 8) - 5
          Bit 1: Overlap # = (overlapStatusGroupNumber * 8) - 6
          Bit 0: Overlap # = (overlapStatusGroupNumber * 8) - 7
       <DescriptiveName> NTCIP-1202::ASC.overlapStatusGroupYellows
       <DataConceptType> Data Element"
::= { overlapStatusGroupEntry 3 }

-- 2.10.4.4 OVERLAP STATUS GROUP GREENS

overlapStatusGroupGreens   OBJECT-TYPE
   SYNTAX   INTEGER (0..255)
   ACCESS   read-only
   STATUS   mandatory
   DESCRIPTION
      "<Definition> Overlap Green Output Status Mask, when 
       a bit=1, the Overlap Green is currently active. When 
       a bit=0, the Overlap Green is NOT currently active.
          Bit 7: Overlap # = (overlapStatusGroupNumber * 8)
          Bit 6: Overlap # = (overlapStatusGroupNumber * 8) - 1
          Bit 5: Overlap # = (overlapStatusGroupNumber * 8) - 2
          Bit 4: Overlap # = (overlapStatusGroupNumber * 8) - 3
          Bit 3: Overlap # = (overlapStatusGroupNumber * 8) - 4
          Bit 2: Overlap # = (overlapStatusGroupNumber * 8) - 5
          Bit 1: Overlap # = (overlapStatusGroupNumber * 8) - 6
          Bit 0: Overlap # = (overlapStatusGroupNumber * 8) - 7
       <DescriptiveName> NTCIP-1202::ASC.overlapStatusGroupGreens
       <DataConceptType> Data Element"
::= { overlapStatusGroupEntry 4 }

-- 2.11 TS2 PORT 1 PARAMETERS

ts2port1  OBJECT IDENTIFIER
::= { asc 10 }

-- This object is an identifier used to group all objects for 
-- support of NEMA TS 2 (Clause 3.3.1) Port 1 activities.

-- 2.11.1 MAXIMUM PORT 1 ADDRESSES

maxPort1Addresses   OBJECT-TYPE
   SYNTAX   INTEGER (1..255)
   ACCESS   read-only
   STATUS   mandatory
   DESCRIPTION
      "<Definition> The Maximum Number of Port 1 addresses 
       this Actuated Controller Unit supports. This object 
       indicates the maximum rows which shall appear in the 
       port1Table object.
       <DescriptiveName> NTCIP-1202::ASC.maxPort1Addresses
       <DataConceptType> Data Element
       <Unit> address"
::= { ts2port1 1 }

-- 2.11.2 PORT 1 TABLE

port1Table   OBJECT-TYPE
   SYNTAX   SEQUENCE OF Port1Entry
   ACCESS   not-accessible
   STATUS   mandatory
   DESCRIPTION
      "<Definition> A table containing Actuated Controller 
       Unit port 1 parameters. The number of rows in this 
       table is equal to maxPort1Addresses object. Address 
       255 is reserved for the all stations (link devices) 
       address.
       <TableType> static
       <DescriptiveName> NTCIP-1202::ASC.port1Table
       <DataConceptType> Entity Type"
::= { ts2port1 2 }


port1Entry   OBJECT-TYPE
   SYNTAX   Port1Entry
   ACCESS   not-accessible
   STATUS   mandatory
   DESCRIPTION
      "<Definition> This object defines a conceptual row in 
       the port 1 Table.
       <DescriptiveName> NTCIP-1202::ASC.port1Entry
       <DataConceptType> Entity Type"
   INDEX { port1Number }
::= { port1Table 1 }

Port1Entry ::= SEQUENCE {
   port1Number          INTEGER,
   port1DevicePresent   INTEGER,
   port1Frame40Enable   INTEGER,
   port1Status          INTEGER,
   port1FaultFrame      INTEGER }

-- 2.11.2.1 PORT 1 NUMBER

port1Number   OBJECT-TYPE
   SYNTAX   INTEGER (1..255)
   ACCESS   read-only
   STATUS   mandatory
   DESCRIPTION
      "<Definition> The (Port 1 address plus one) for 
       objects in this row. This value shall not exceed the 
       maxPort1Addresses object value.
       <DescriptiveName> NTCIP-1202::ASC.port1Number
       <DataConceptType> Data Element
       <Unit> address"
::= { port1Entry 1 }

-- 2.11.2.2 PORT 1 DEVICE PRESENT

port1DevicePresent   OBJECT-TYPE
   SYNTAX   INTEGER (0..1)
   ACCESS   read-write
   STATUS   mandatory
   DESCRIPTION
      "<Definition> This object is used to program the CU as to 
       the presence or absence of a device for this Port 1 address. 
       The CU shall transmit Command Frames only to those devices 
       that are present as determined by this programming.
          True (one) - the device is present. 
          False (zero) - the device is not present.
       <DescriptiveName> NTCIP-1202::ASC.port1DevicePresent
       <DataConceptType> Data Element"
   REFERENCE
      "NEMA TS 2 Clause 3.3.1.4"
::= { port1Entry 2 }


-- 2.11.2.3 PORT 1 FRAME 40 ENABLE

port1Frame40Enable   OBJECT-TYPE
   SYNTAX   INTEGER (0..1)
   ACCESS   read-write
   STATUS   mandatory
   DESCRIPTION
      "<Definition> To enable or disable Frame 40 messages 
       to the device at this Port 1 address. Frame 40 is 
       used to poll the secondary stations for a secondary 
       to secondary message exchange. Command 40 series 
       frames shall be transmitted only to those devices 
       that are enabled, as determined by this programming.
          TRUE (one) - Enable frame 40 messages for 
             this device.
          FALSE (zero) - Disable frame 40 messages for this 
             device.
       <DescriptiveName> NTCIP-1202::ASC.port1Frame40Enable
       <DataConceptType> Data Element"
   REFERENCE
      "NEMA TS 2 Clause 3.3.1.4.1"
::= { port1Entry 3 }

-- 2.11.2.4 PORT 1 STATUS

port1Status   OBJECT-TYPE
   SYNTAX   INTEGER { other (1),
                      online (2),
                      responseFault (3) }
   ACCESS   read-only
   STATUS   mandatory
   DESCRIPTION
      "<Definition> This object indicates the 
       communications status with the associated device:
          other: This indicates that some other 
             communications faulthas been detected.
          online: This indicates that at least five of the 
             most recent 10 response transfers were 
             received correctly.
          responseFault: This indicates that more than 5 of 
             the most recent 10 response transfers were 
             received incorrectly.
       <DescriptiveName> NTCIP-1202::ASC.port1Status
       <DataConceptType> Data Element"
::= { port1Entry 4 }

-- 2.11.2.5 PORT 1 FAULT FRAME

port1FaultFrame   OBJECT-TYPE
   SYNTAX   INTEGER  (0..255)
   ACCESS   read-only
   STATUS   mandatory
   DESCRIPTION
      "<Definition> This object indicates the frame number 
       that caused the most recent fault.

       <DescriptiveName> NTCIP-1202::ASC.port1FaultFrame
       <DataConceptType> Data Element"
::= { port1Entry 5 }

-- 2.12 ASC BLOCK OBJECTS

ascBlock  OBJECT IDENTIFIER
::= { asc 11 }

-- This object is an identifier used to group all objects for 
-- support of ASC Block Upload and Download activities.

-- 2.12.1 ASC BLOCK GET CONTROL

ascBlockGetControl   OBJECT-TYPE
   SYNTAX   OCTET STRING (SIZE(2..12))
   ACCESS   read-write
   STATUS   mandatory
   DESCRIPTION
      "<Definition> An OER encoded string of reference 
       parameters for ASC Block Uploads. The parameter 
       values in this string are:
         ascBlockDataType    INTEGER (0..255)
         ascBlockDataID      INTEGER (0..255)
         ascBlockIndex1      INTEGER (0..255) if needed
         ascBlockQuantity1   INTEGER (0..255) if needed
         ascBlockIndex2      INTEGER (0..255) if needed
         ascBlockQuantity2   INTEGER (0..255) if needed
         ascBlockIndex3      INTEGER (0..255) if needed
         ascBlockQuantity3   INTEGER (0..255) if needed
         ascBlockIndex4      INTEGER (0..255) if needed
         ascBlockQuantity4   INTEGER (0..255) if needed
         ascBlockIndex5      INTEGER (0..255) if needed
         ascBlockQuantity5   INTEGER (0..255) if needed

       A GET of ascBlockData shall utilize values currently 
       in this object to define the data to be returned.

       A SET of this object shall be evaluated for validity 
       and Error Status of badValue(3) be returned for the 
       following conditions:
        1) ascBlockDataType is not supported
        2) ascBlockDataID is not supported
        3) ascBlockIndex1 is zero or not supported
        4) ascBlockQuantity1 is zero or
           ascBlockIndex1 + ascBlockQuantity1 - 1 is not 
           supported
        5) ascBlockIndex2 is zero or not supported
        6) ascBlockQuantity2 is zero or
           ascBlockIndex2 + ascBlockQuantity2) - 1 is not 
           supported
        7) ascBlockIndex3 is zero or not supported
        8) ascBlockQuantity3 is zero or
           ascBlockIndex3 + ascBlockQuantity3) - 1 is not 
           supported
        9) ascBlockIndex4 is zero or not supported

       10) ascBlockQuantity4 is zero or
           ascBlockIndex4 + ascBlockQuantity4) - 1 is not 
           supported
       11) ascBlockIndex5 is zero or not supported
       12) ascBlockQuantity5 is zero or
           ascBlockIndex5 + ascBlockQuantity5) - 1 is not 
           supported
       13) if the SET length is zero or incorrect for
           ascBlockDataType & ascBlockDataID
       14) if the GetResponse length for a GET on 
           ascBlockData using maximum data field sizes 
           would exceed a local limitation
       When this validity check fails, ascBlockErrorStatus 
       shall be set equal to the Bullet Value above that 
       generated the error.
       <DescriptiveName> NTCIP-1202::ASC.ascBlockGetControl
       <DataConceptType> Data Frame
       <Unit> "
::= { ascBlock 1 }

-- 2.12.2 ASC BLOCK DATA

ascBlockData   OBJECT-TYPE
   SYNTAX   OCTET STRING (SIZE(2..484))
   ACCESS  read-write
   STATUS  mandatory
   DESCRIPTION
      "<Definition> An OER encoded string used for 
       uploading and downloading ASC parameters. See 
       SECTION 3 for encoding and decoding the block.

       A SET on this object shall require the use of 
       'dbCreateTransaction' defined in NTCIP 1201 
       Clause 2.3.1.

       A SET of this object shall be evaluated for validity 
       and Error Status of badValue(3) be returned for the 
       following conditions:
        1) ascBlockDataType is not supported
        2) ascBlockDataID is not supported
        3) ascBlockIndex1 is zero or not supported
        4) ascBlockQuantity1 is zero or
           ascBlockIndex1 + ascBlockQuantity1 - 1 is not 
           supported
        5) ascBlockIndex2 is zero or not supported
        6) ascBlockQuantity2 is zero or
           ascBlockIndex2 + ascBlockQuantity2) - 1 is not 
           supported
        7) ascBlockIndex3 is zero or not supported
        8) ascBlockQuantity3 is zero or
           ascBlockIndex3 + ascBlockQuantity3) - 1 is not 
           supported
        9) ascBlockIndex4 is zero or not supported
       10) ascBlockQuantity4 is zero or
           ascBlockIndex4 + ascBlockQuantity4) - 1 is not 
           supported
       11) ascBlockIndex5 is zero or not supported
       12) ascBlockQuantity5 is zero or
           ascBlockIndex5 + ascBlockQuantity5) - 1 is not 
           supported
       13) if the SET length is zero or incorrect for
           ascBlockDataType & ascBlockDataID
       14) if the SET (SEQUENCE OF) value is incorrect.
       When this validity check fails, ascBlockErrorStatus 
       shall be set equal to the Bullet Value above that 
       generated the error.

       A SET that includes an unsupported value for a 
       supported data element shall return an Error Status 
       of badValue(3) and ascBlockErrorStatus shall be set 
       equal to:
          (data Sequence # * 100) + data Element #

       A SET that includes a non-zero or non-null value in 
       the position of an unsupported data element shall 
       return an Error Status of badValue(3) and 
       ascBlockErrorStatus shall be set equal to:
          (data Sequence # * 100) + data Element #

       A GET on this object shall utilize values currently in
       ascBlockGetControl to define the data to be returned.
       When ascBlockGetControl has invalid data, an Error 
       Status of badValue(3) shall be returned.

       A GET shall return a zero or null value in the position 
       of an unsupported object.
       <DescriptiveName> NTCIP-1202::ASC.ascBlockData
       <DataConceptType> Data Frame
       <Unit> "
::= { ascBlock 2 }

-- 2.12.3 ASC BLOCK ERROR STATUS

ascBlockErrorStatus   OBJECT-TYPE
   SYNTAX   INTEGER (0..65535)
   ACCESS   read-only
   STATUS   mandatory
   DESCRIPTION
      "<Definition> This object defines the data element 
       within ascBlockGetControl or ascBlockData that
       caused a badValue(3) ErrorStatus.
         This object should equal zero after any successful
       SET to ascBlockGetControl or ascBlockData.
       <DescriptiveName> NTCIP-1202::ASC.ascBlockErrorStatus
       <DataConceptType> Data Element"
::= { ascBlock 3 }

END
